------------------------------------------------------------------------------
-- Radisys Limited (was 3Way Networks Ltd)
-- FAP SNMP MIB Definition
------------------------------------------------------------------------------
-- $LastChangedRevision: 28222 $
-- $LastChangedDate: 2010-07-15 15:59:32 +0530 (Thu, 15 Jul 2010) $
------------------------------------------------------------------------------
--

IN-C-SNMP-MIB DEFINITIONS ::= BEGIN

IMPORTS
    enterprises FROM RFC1155-SMI
    OBJECT-TYPE FROM RFC-1212
    TRAP-TYPE FROM RFC-1215;

threeWayNetworks OBJECT IDENTIFIER ::= { enterprises 26142 }

inC                     OBJECT IDENTIFIER ::= { threeWayNetworks 1 }

mibObjects              OBJECT IDENTIFIER ::= {   inC 1 }
topLevelCellConfig      OBJECT IDENTIFIER ::= {     mibObjects 1 }
sib1CellConfig          OBJECT IDENTIFIER ::= {     mibObjects 2 }
sib3CellConfig          OBJECT IDENTIFIER ::= {     mibObjects 3 }
-- Access Restriction
accessRestriction       OBJECT IDENTIFIER ::= {     sib3CellConfig 30 }

sib5CellConfig          OBJECT IDENTIFIER ::= {     mibObjects 4 }
sib7CellConfig          OBJECT IDENTIFIER ::= {     mibObjects 5 }

congestionRedirection   OBJECT IDENTIFIER ::= { topLevelCellConfig 12 }

-- Neighbour cells including SIB11 config.
neighbourCellConfig     OBJECT IDENTIFIER ::= {     mibObjects 6 }

-- Intra-Frequency Neighbour Cells.
intraFreqNeighbourCells OBJECT IDENTIFIER ::= {       neighbourCellConfig 10 }
intraCell0             OBJECT IDENTIFIER ::= {         intraFreqNeighbourCells 1 }
intraCell1             OBJECT IDENTIFIER ::= {         intraFreqNeighbourCells 2 }
intraCell2             OBJECT IDENTIFIER ::= {         intraFreqNeighbourCells 3 }
intraCell3             OBJECT IDENTIFIER ::= {         intraFreqNeighbourCells 4 }
intraCell4             OBJECT IDENTIFIER ::= {         intraFreqNeighbourCells 5 }
intraCell5             OBJECT IDENTIFIER ::= {         intraFreqNeighbourCells 6 }

-- Inter-Frequency Neighbour Cells.
interFreqNeighbourCells OBJECT IDENTIFIER ::= {       neighbourCellConfig 11 }
interCell0             OBJECT IDENTIFIER ::= {         interFreqNeighbourCells 1 }
interCell1             OBJECT IDENTIFIER ::= {         interFreqNeighbourCells 2 }
interCell2             OBJECT IDENTIFIER ::= {         interFreqNeighbourCells 3 }
interCell3             OBJECT IDENTIFIER ::= {         interFreqNeighbourCells 4 }
interCell4             OBJECT IDENTIFIER ::= {         interFreqNeighbourCells 5 }
interCell5             OBJECT IDENTIFIER ::= {         interFreqNeighbourCells 6 }

-- Inter-RAT (GSM) Neighbour Cells.
interRatNeighbourCells  OBJECT IDENTIFIER ::= {       neighbourCellConfig 12 }
interRatCell0          OBJECT IDENTIFIER ::= {         interRatNeighbourCells 1 }
interRatCell1          OBJECT IDENTIFIER ::= {         interRatNeighbourCells 2 }
interRatCell2          OBJECT IDENTIFIER ::= {         interRatNeighbourCells 3 }
interRatCell3          OBJECT IDENTIFIER ::= {         interRatNeighbourCells 4 }
interRatCell4          OBJECT IDENTIFIER ::= {         interRatNeighbourCells 5 }
interRatCell5          OBJECT IDENTIFIER ::= {         interRatNeighbourCells 6 }

management              OBJECT IDENTIFIER ::= {     mibObjects 7 }
tr069                   OBJECT IDENTIFIER ::= {       management 6 }
configurationServer     OBJECT IDENTIFIER ::= {         tr069 2 }
licensing               OBJECT IDENTIFIER ::= {       management 7 }

ipSettings              OBJECT IDENTIFIER ::= {     mibObjects 8 }
ike                     OBJECT IDENTIFIER ::= {       ipSettings 8 }
qos                     OBJECT IDENTIFIER ::= {       ipSettings 9 }

iuInterface             OBJECT IDENTIFIER ::= {     mibObjects 9 }
iuAddressing            OBJECT IDENTIFIER ::= {       iuInterface 1 }
sctp                    OBJECT IDENTIFIER ::= {       iuInterface 2 }
m3ua                    OBJECT IDENTIFIER ::= {       iuInterface 3 }
sccp                    OBJECT IDENTIFIER ::= {       iuInterface 4 }
ranap                   OBJECT IDENTIFIER ::= {       iuInterface 5 }
closedAccessControl     OBJECT IDENTIFIER ::= {       iuInterface 6 }
relocation              OBJECT IDENTIFIER ::= {       iuInterface 7 }

intraFrequencyHandoverControl OBJECT IDENTIFIER ::= {   relocation 41 }
event-1c                OBJECT IDENTIFIER ::= {           intraFrequencyHandoverControl 1 }
event-1e                OBJECT IDENTIFIER ::= {           intraFrequencyHandoverControl 2 }
event-1f                OBJECT IDENTIFIER ::= {           intraFrequencyHandoverControl 3 }

interFrequencyHandoverControl OBJECT IDENTIFIER ::= {   relocation 42 }
-- no longer used here - event-1e                OBJECT IDENTIFIER ::= {           interFrequencyHandoverControl 1 }
-- no longer used here - event-1f                OBJECT IDENTIFIER ::= {           interFrequencyHandoverControl 2 }
event-2a                OBJECT IDENTIFIER ::= {           interFrequencyHandoverControl 3 }
event-2b                OBJECT IDENTIFIER ::= {           interFrequencyHandoverControl 4 }
event-2c                OBJECT IDENTIFIER ::= {           interFrequencyHandoverControl 5 }
event-2d-inter          OBJECT IDENTIFIER ::= {           interFrequencyHandoverControl 6 }
event-2f-inter          OBJECT IDENTIFIER ::= {           interFrequencyHandoverControl 7 }

interSystemHandoverControl    OBJECT IDENTIFIER ::= {   relocation 43 }
event-3a                OBJECT IDENTIFIER ::= {           interSystemHandoverControl 1 }
event-2d-rat            OBJECT IDENTIFIER ::= {           interSystemHandoverControl 2 }
event-2f-rat            OBJECT IDENTIFIER ::= {           interSystemHandoverControl 3 }

freqSync                OBJECT IDENTIFIER ::= {     mibObjects 10 }
provisioningParams      OBJECT IDENTIFIER ::= {     mibObjects 11 }
powerControlParams      OBJECT IDENTIFIER ::= {     mibObjects 12 }
rrmParams               OBJECT IDENTIFIER ::= {     mibObjects 13 }
pppoeParams             OBJECT IDENTIFIER ::= {     mibObjects 14 }

-- REM scan config and results
remScan                 OBJECT IDENTIFIER ::= {     mibObjects 15 }
remScanConfig           OBJECT IDENTIFIER ::= {     remScan 1 }
freqScanConfig          OBJECT IDENTIFIER ::= {     remScan 2 }
ncScanConfig            OBJECT IDENTIFIER ::= {     remScan 3 }
remScanStatus           OBJECT IDENTIFIER ::= {     remScan 4 }
freqScanResults         OBJECT IDENTIFIER ::= {     remScan 5 }
ncScanResults           OBJECT IDENTIFIER ::= {     remScan 6 }

-- Intra-Frequency Neighbour Cells.
ncScanIntraFreqNeighbourCells OBJECT IDENTIFIER ::= {       ncScanResults 5 }
ncScanIntraCell0             OBJECT IDENTIFIER ::= {         ncScanIntraFreqNeighbourCells 1 }
ncScanIntraCell1             OBJECT IDENTIFIER ::= {         ncScanIntraFreqNeighbourCells 2 }
ncScanIntraCell2             OBJECT IDENTIFIER ::= {         ncScanIntraFreqNeighbourCells 3 }
ncScanIntraCell3             OBJECT IDENTIFIER ::= {         ncScanIntraFreqNeighbourCells 4 }
ncScanIntraCell4             OBJECT IDENTIFIER ::= {         ncScanIntraFreqNeighbourCells 5 }
ncScanIntraCell5             OBJECT IDENTIFIER ::= {         ncScanIntraFreqNeighbourCells 6 }

-- Inter-Frequency Neighbour Cells.
ncScanInterFreqNeighbourCells OBJECT IDENTIFIER ::= {       ncScanResults 6 }
ncScanInterCell0             OBJECT IDENTIFIER ::= {         ncScanInterFreqNeighbourCells 1 }
ncScanInterCell1             OBJECT IDENTIFIER ::= {         ncScanInterFreqNeighbourCells 2 }
ncScanInterCell2             OBJECT IDENTIFIER ::= {         ncScanInterFreqNeighbourCells 3 }
ncScanInterCell3             OBJECT IDENTIFIER ::= {         ncScanInterFreqNeighbourCells 4 }
ncScanInterCell4             OBJECT IDENTIFIER ::= {         ncScanInterFreqNeighbourCells 5 }
ncScanInterCell5             OBJECT IDENTIFIER ::= {         ncScanInterFreqNeighbourCells 6 }

-- Inter-RAT (GSM) Neighbour Cells.
ncScanInterRatNeighbourCells  OBJECT IDENTIFIER ::= {       ncScanResults 7 }
ncScanInterRatCell0          OBJECT IDENTIFIER ::= {         ncScanInterRatNeighbourCells 1 }
ncScanInterRatCell1          OBJECT IDENTIFIER ::= {         ncScanInterRatNeighbourCells 2 }
ncScanInterRatCell2          OBJECT IDENTIFIER ::= {         ncScanInterRatNeighbourCells 3 }
ncScanInterRatCell3          OBJECT IDENTIFIER ::= {         ncScanInterRatNeighbourCells 4 }
ncScanInterRatCell4          OBJECT IDENTIFIER ::= {         ncScanInterRatNeighbourCells 5 }
ncScanInterRatCell5          OBJECT IDENTIFIER ::= {         ncScanInterRatNeighbourCells 6 }

mibEngObjects           OBJECT IDENTIFIER ::= {   inC 2 }
factory                 OBJECT IDENTIFIER ::= {     mibEngObjects 2 }
hwFeatures              OBJECT IDENTIFIER ::= {     mibEngObjects 3 }
trace                   OBJECT IDENTIFIER ::= {     mibEngObjects 4 }

traps                   OBJECT IDENTIFIER ::= {   inC 3 }


-- topLevelCellConfig

mnc OBJECT-TYPE
    SYNTAX Unsigned32 (0..999)
    ACCESS read-write
    STATUS optional
    DESCRIPTION "Mobile Network Code (MNC)"
    ::= { topLevelCellConfig 1 }

mcc OBJECT-TYPE
    SYNTAX Unsigned32 (0..999)
    ACCESS read-write
    STATUS optional
    DESCRIPTION "Mobile Country Code (MCC)"
    ::= { topLevelCellConfig 2 }

dlUArfcn OBJECT-TYPE
    SYNTAX Unsigned32 (412..10838)
    ACCESS read-write
    STATUS optional
    DESCRIPTION "Downlink UARFCN
                 2100 band 10562..10838
                 1900 band 9662..9938
                           412, 437, 462, 487, 512, 537, 562, 587, 612, 637, 662, 687"
    ::= { topLevelCellConfig 3 }

dlPrimaryScramblingCode OBJECT-TYPE
    SYNTAX Unsigned32 (0..511)
    ACCESS read-write
    STATUS optional
    DESCRIPTION "Downlink Primary Scrambling Code"
    ::= { topLevelCellConfig 4 }

lac OBJECT-TYPE
    SYNTAX Unsigned32 (0..65535)
    ACCESS read-write
    STATUS optional
    DESCRIPTION "Location Area Code (LAC)"
    ::= { topLevelCellConfig 5 }

rac OBJECT-TYPE
    SYNTAX Unsigned32 (0..255)
    ACCESS read-write
    STATUS optional
    DESCRIPTION "Routing Area Code (RAC)"
    ::= { topLevelCellConfig 7 }

sac OBJECT-TYPE
    SYNTAX Unsigned32 (0..65535)
    ACCESS read-write
    STATUS optional
    DESCRIPTION "Service Area Code (SAC)"
    ::= { topLevelCellConfig 8 }

rncId OBJECT-TYPE
    SYNTAX Unsigned32 (0..4095)
    ACCESS read-write
    STATUS optional
    DESCRIPTION "RNC ID"
    ::= { topLevelCellConfig 9 }

l2CypheringEnable OBJECT-TYPE
    SYNTAX Unsigned32 (0..1)
    ACCESS read-write
    STATUS optional
    DESCRIPTION "Layer 2 Cyphering Enable"
    ::= { topLevelCellConfig 10 }

rlcAckTimer OBJECT-TYPE
    SYNTAX Unsigned32 (1..65535)
    ACCESS read-write
    STATUS optional
    DESCRIPTION "Number of seconds to wait for Acknowledge of AM Tx in RLC"
    ::= { topLevelCellConfig 11 }

-- Congestion redirection

congestionRetryTimer OBJECT-TYPE
    SYNTAX Unsigned32 (0..15)
    ACCESS read-write
    STATUS optional
    DESCRIPTION "Defines the number of seconds the UE has to 
                 wait before repeating the rejected RRC procedure:
                 0 = Do Not Retry"
    ::= { congestionRedirection 1 }

redirectOnCongestion OBJECT-TYPE
    SYNTAX Unsigned32 (0..2)
    ACCESS read-write
    STATUS optional
    DESCRIPTION "When the FAP has 4 active users, 
                 should we redirect to another cell?
                 0 = No; UE should retry apply 'congestionRetryTimer'.
                 1 = Redirect to defined UMTS cell.
                 2 = Redirect to GSM.
                     Rel 6: Redirect to defined GSM cell."
    ::= { congestionRedirection 2 }

congestionRedirectWaitTimer OBJECT-TYPE
    SYNTAX Unsigned32 (0..15)
    ACCESS read-write
    STATUS optional
    DESCRIPTION "Defines the number of seconds the UE has to 
                 wait before redirecting to the defined cell.
                 0 = Do Not Retry"
    ::= { congestionRedirection 3 }

-- SIB1

csDomainEnable OBJECT-TYPE
    SYNTAX Unsigned32 (0..1)
    ACCESS read-write
    STATUS optional
    DESCRIPTION "CS Domain Enable"
    ::= { sib1CellConfig 1 }

psDomainEnable OBJECT-TYPE
    SYNTAX Unsigned32 (0..1)
    ACCESS read-write
    STATUS optional
    DESCRIPTION "PS Domain Enable"
    ::= { sib1CellConfig 2 }

networkModeOfOperation OBJECT-TYPE
    SYNTAX Unsigned32 (0..1)
    ACCESS read-write
    STATUS optional
    DESCRIPTION "Network Mode of Operation.
                 0=Mode I, 1=Mode II"
    ::= { sib1CellConfig 3 }

t3212 OBJECT-TYPE
    SYNTAX Unsigned32 (0..255)
    ACCESS read-write
    STATUS optional
    DESCRIPTION "T3212 Periodic Location Update timer (decihours)
                 0=No periodic update"
    ::= { sib1CellConfig 4 }

allowGuestRoaming OBJECT-TYPE
    SYNTAX Unsigned32 (0..1)
    ACCESS read-write
    STATUS optional
    DESCRIPTION "Allow subscriber roaming in target cell"
    ::= { sib1CellConfig 5 }

t313 OBJECT-TYPE
    SYNTAX Unsigned32 (0..15)
    ACCESS read-write
    STATUS optional
    DESCRIPTION "T313 timer. Seconds"
    ::= { sib1CellConfig 6 }

n313 OBJECT-TYPE
    SYNTAX Unsigned32 (0..7)
    ACCESS read-write
    STATUS optional
    DESCRIPTION "N313 constant.
                 1s = 0, 2s = 1,
                 4s = 2, 10s = 3,
                 20s = 4, 50s = 5,
                 100s = 6, 200s = 7"
    ::= { sib1CellConfig 7 }

t312 OBJECT-TYPE
    SYNTAX Unsigned32 (0..15)
    ACCESS read-write
    STATUS optional
    DESCRIPTION "T312 timer. Seconds"
    ::= { sib1CellConfig 8 }

n312 OBJECT-TYPE
    SYNTAX Unsigned32 (0..10)
    ACCESS read-write
    STATUS optional
    DESCRIPTION "N312 Constant; The number of 'IN SYNC'
                 indications required (during T312 period)
                 before initial connection synchronisation 
                 is said to be achieved.
                 0 =   1 IND Req'd
                 1 =   2 IND Req'd
                 2 =   4 IND Req'd
                 3 =  10 IND Req'd
                 4 =  20 IND Req'd
                 5 =  50 IND Req'd
                 6 = 100 IND Req'd
                 7 = 200 IND Req'd
                 8 = 400 IND Req'd
                 9 = 600 IND Req'd
                10 = 800 IND Req'd"
    ::= { sib1CellConfig 9 }

t302 OBJECT-TYPE
    SYNTAX Unsigned32 (0..15)
    ACCESS read-write
    STATUS optional
    DESCRIPTION "T302 timer.
                 100ms = 0, 200ms = 1,
                 400ms = 2, 600ms = 3,
                 800ms = 4, 1000ms = 5,
                 1200ms = 6, 1400ms = 7,
                 1600ms = 8, 1800ms = 9,
                 2000ms = 10, 3000ms = 11,
                 4000ms = 12, 6000ms = 13,
                 8000ms = 14, spare = 15"
    ::= { sib1CellConfig 10 }

n302 OBJECT-TYPE
    SYNTAX Unsigned32 (0..7)
    ACCESS read-write
    STATUS optional
    DESCRIPTION "N302 constant"
    ::= { sib1CellConfig 11 }

t314 OBJECT-TYPE
    SYNTAX Unsigned32 (0..7)
    ACCESS read-write
    STATUS optional
    DESCRIPTION "T314 timer.
                 0s = 0, 2s = 1,
                 4s = 2, 6s = 3,
                 8s = 4, 12s = 5,
                 16s = 6, 20s = 7"
    ::= { sib1CellConfig 12 }

t315 OBJECT-TYPE
    SYNTAX Unsigned32 (0..7)
    ACCESS read-write
    STATUS optional
    DESCRIPTION "T315 timer.
                 0s = 0, 10s = 1,
                 30s = 2, 60s = 3,
                 180s = 4, 600s = 5,
                 1200s = 6, 1800s = 7"
    ::= { sib1CellConfig 13 }

n315 OBJECT-TYPE
    SYNTAX Unsigned32 (0..10)
    ACCESS read-write
    STATUS optional
    DESCRIPTION "N315 Constant; The number of 'IN SYNC'
                 indications required (during T315 period)
                 before synchronisation is said to be achieved.
                 0 =   1 IND Req'd
                 1 =   2 IND Req'd
                 2 =   4 IND Req'd
                 3 =  10 IND Req'd
                 4 =  20 IND Req'd
                 5 =  50 IND Req'd
                 6 = 100 IND Req'd
                 7 = 200 IND Req'd
                 8 = 400 IND Req'd
                 9 = 600 IND Req'd
                10 = 800 IND Req'd"
    ::= { sib1CellConfig 14 }

t300 OBJECT-TYPE
    SYNTAX Unsigned32 (0..15)
    ACCESS read-write
    STATUS optional
    DESCRIPTION "T300 timer.
                 100ms = 0, 200ms = 1,
                 400ms = 2, 600ms = 3,
                 800ms = 4, 1000ms = 5,
                 1200ms = 6, 1400ms = 7,
                 1600ms = 8, 1800ms = 9,
                 2000ms = 10, 3000ms = 11,
                 4000ms = 12, 6000ms = 13,
                 8000ms = 14, spare = 15"
    ::= { sib1CellConfig 15 }

n300 OBJECT-TYPE
    SYNTAX Unsigned32 (0..7)
    ACCESS read-write
    STATUS optional
    DESCRIPTION "N302 constant"
    ::= { sib1CellConfig 16 }

drxPagingCoeff OBJECT-TYPE
    SYNTAX Unsigned32 (6..9)
    ACCESS read-write
    STATUS optional
    DESCRIPTION "Drx Paging Cycle Length Coeff"
    ::= { sib1CellConfig 17 }

-- SIB3

cellIdentity OBJECT-TYPE
    SYNTAX Unsigned32 (0..268435455)
    ACCESS read-write
    STATUS optional
    DESCRIPTION "Cell Identity"
    ::= { sib3CellConfig 1 }

sIntraSearch OBJECT-TYPE
    SYNTAX INTEGER (-32..20)
    ACCESS read-write
    STATUS optional
    DESCRIPTION "s_Intra_Search (dB)"
    ::= { sib3CellConfig 2 }

qQualMin OBJECT-TYPE
    SYNTAX INTEGER (-24..0)
    ACCESS read-write
    STATUS optional
    DESCRIPTION "q_Qual_Min (dB)"
    ::= { sib3CellConfig 3 }

-- TEMS: 1:-115 2:-111 3:-111 4:-107
qRxLevMin OBJECT-TYPE
    SYNTAX INTEGER (-115..-25)
    ACCESS read-write
    STATUS optional
    DESCRIPTION "q_RX_Lev_Min (dBm)"
    ::= { sib3CellConfig 4 }

qHyst1S OBJECT-TYPE
    SYNTAX Unsigned32 (0..40)
    ACCESS read-write
    STATUS optional
    DESCRIPTION "q_Hyst_1_S (dB)"
    ::= { sib3CellConfig 5 }

tReselection OBJECT-TYPE
    SYNTAX Unsigned32 (0..31)
    ACCESS read-write
    STATUS optional
    DESCRIPTION "T_Reselection (s)"
    ::= { sib3CellConfig 6 }

maxAllowedUlPower OBJECT-TYPE
    SYNTAX INTEGER (-50..33)
    ACCESS read-write
    STATUS optional
    DESCRIPTION "Maximum Allowed U/L TX Power (dBm)"
    ::= { sib3CellConfig 7 }

qHyst2S OBJECT-TYPE
    SYNTAX Unsigned32 (0..40)
    ACCESS read-write
    STATUS optional
    DESCRIPTION "q_Hyst_2_S (dB)"
    ::= { sib3CellConfig 8 }

sInterSearch OBJECT-TYPE
    SYNTAX INTEGER (-32..20)
    ACCESS read-write
    STATUS optional
    DESCRIPTION "s_Inter_Search (dB)"
    ::= { sib3CellConfig 9 }

sSearchHCS OBJECT-TYPE
    SYNTAX INTEGER (-105..91)
    ACCESS read-write
    STATUS optional
    DESCRIPTION "s_SearchHCS"
    ::= { sib3CellConfig 10 }

hcsPRIO OBJECT-TYPE
    SYNTAX Unsigned32 (0..7)
    ACCESS read-write
    STATUS optional
    DESCRIPTION "HCS Priority"
    ::= { sib3CellConfig 11 }

qHCS OBJECT-TYPE
    SYNTAX Unsigned32 (0..99)
    ACCESS read-write
    STATUS optional
    DESCRIPTION "Quality Threshold for HCS"
    ::= { sib3CellConfig 12 }

nCR OBJECT-TYPE
    SYNTAX Unsigned32 (1..16)
    ACCESS read-write
    STATUS optional
    DESCRIPTION "Maximum Number of Cell Reselections"
    ::= { sib3CellConfig 13 }

tCRMax OBJECT-TYPE
    SYNTAX Unsigned32 (1..6)
    ACCESS read-write
    STATUS optional
    DESCRIPTION "Maximum t_CR"
    ::= { sib3CellConfig 14 }

tCRMaxHyst OBJECT-TYPE
    SYNTAX Unsigned32 (0..7)
    ACCESS read-write
    STATUS optional
    DESCRIPTION "Maximum Hysteresis for t_CR"
    ::= { sib3CellConfig 15 }

qHyst2SPresent OBJECT-TYPE
    SYNTAX Unsigned32 (0..1)
    ACCESS read-write
    STATUS optional
    DESCRIPTION "q_Hyst_2_S Present (boolean)"
    ::= { sib3CellConfig 16 }

sInterSearchPresent OBJECT-TYPE
    SYNTAX Unsigned32 (0..1)
    ACCESS read-write
    STATUS optional
    DESCRIPTION "s_Inter_Search Present (boolean)"
    ::= { sib3CellConfig 17 }

sSearchHCSPresent OBJECT-TYPE
    SYNTAX Unsigned32 (0..1)
    ACCESS read-write
    STATUS optional
    DESCRIPTION "s_SearchHCS Present (boolean)"
    ::= { sib3CellConfig 18 }

-- hcsServingCellInfoPresent 19  removed

nCRPresent OBJECT-TYPE
    SYNTAX Unsigned32 (0..1)
    ACCESS read-write
    STATUS optional
    DESCRIPTION "nCR Present (boolean)"
    ::= { sib3CellConfig 20 }

useRSCP OBJECT-TYPE
    SYNTAX Unsigned32 (0..1)
    ACCESS read-write
    STATUS optional
    DESCRIPTION "Use RSCP (instead of EcN0)"
    ::= { sib3CellConfig 21 }

-- Access Restrictions

cellBarred OBJECT-TYPE
    SYNTAX Unsigned32 (0..1)
    ACCESS read-write
    STATUS optional
    DESCRIPTION "Cell Barred"
    ::= { accessRestriction 1 }

tBarred OBJECT-TYPE
    SYNTAX Unsigned32 (0..7)
    ACCESS read-write
    STATUS optional
    DESCRIPTION "Cell Barred Period"
    ::= { accessRestriction 2 }

intraCellReselInd OBJECT-TYPE
    SYNTAX Unsigned32 (0..1)
    ACCESS read-write
    STATUS optional
    DESCRIPTION "Intra Frequency Reselection Indicator"
    ::= { accessRestriction 3 }
    
acBarredListMask OBJECT-TYPE
    SYNTAX Unsigned32 (0..65535)
    ACCESS read-write
    STATUS optional
    DESCRIPTION "Access Class Barred List Mask"
    ::= { accessRestriction 4 }

cellRestrictions OBJECT-TYPE
    SYNTAX Unsigned32 (0..1)
    ACCESS read-write
    STATUS optional
    DESCRIPTION "Cell Restrictions"
    ::= { accessRestriction 5 }

percentageBarredACCell OBJECT-TYPE
    SYNTAX Unsigned32 (1..3)
    ACCESS read-write
    STATUS optional
    DESCRIPTION "Percentage of Barred Access Classes for Cell"
    ::= { accessRestriction 6 }

periodicACBarringCell OBJECT-TYPE
    SYNTAX Unsigned32 (0..1)
    ACCESS read-write
    STATUS optional
    DESCRIPTION "Periodic Access Class Barring for Cell"
    ::= { accessRestriction 7 }

restrictionPeriod OBJECT-TYPE
    SYNTAX Unsigned32 (0..100)
    ACCESS read-write
    STATUS optional
    DESCRIPTION "Restriction Period"
    ::= { accessRestriction 8 }
-- DSAC
acBarredListCSMask OBJECT-TYPE
    SYNTAX Unsigned32 (0..65535)
    ACCESS read-write
    STATUS optional
    DESCRIPTION "Access Class Barred List Mask for CS"
    ::= { accessRestriction 9 }

csDomainRestrictions OBJECT-TYPE
    SYNTAX Unsigned32 (0..1)
    ACCESS read-write
    STATUS optional
    DESCRIPTION "CS Domain Restrictions"
    ::= { accessRestriction 10 }

percentageBarredACCS OBJECT-TYPE
    SYNTAX Unsigned32 (1..3)
    ACCESS read-write
    STATUS optional
    DESCRIPTION "Percentage of Barred Access Classes for CS"
    ::= { accessRestriction 11 }

periodicACBarringCS OBJECT-TYPE
    SYNTAX Unsigned32 (0..1)
    ACCESS read-write
    STATUS optional
    DESCRIPTION "Periodic Access Class Barring for CS"
    ::= { accessRestriction 12 }

acBarredListPSMask OBJECT-TYPE
    SYNTAX Unsigned32 (0..65535)
    ACCESS read-write
    STATUS optional
    DESCRIPTION "Access Class Barred List Mask for PS"
    ::= { accessRestriction 13 }

psDomainRestrictions OBJECT-TYPE
    SYNTAX Unsigned32 (0..1)
    ACCESS read-write
    STATUS optional
    DESCRIPTION "PS Domain Restrictions"
    ::= { accessRestriction 14 }

percentageBarredACPS OBJECT-TYPE
    SYNTAX Unsigned32 (1..3)
    ACCESS read-write
    STATUS optional
    DESCRIPTION "Percentage of Barred Access Classes for PS"
    ::= { accessRestriction 15 }

periodicACBarringPS OBJECT-TYPE
    SYNTAX Unsigned32 (0..1)
    ACCESS read-write
    STATUS optional
    DESCRIPTION "Periodic Access Class Barring for PS"
    ::= { accessRestriction 16 }
    
-- SIB5

primaryCPICHTxPower OBJECT-TYPE
    SYNTAX INTEGER (-10..50)
    ACCESS read-only
    STATUS optional
    DESCRIPTION "Primary CPICH TX Power (dBm)
                 READ ONLY - calculated from power control parameters."
    ::= { sib5CellConfig 1 }

constantValue OBJECT-TYPE
    SYNTAX INTEGER (-35..-10)
    ACCESS read-write
    STATUS optional
    DESCRIPTION "Power Control Constant Value (dB)"
    ::= { sib5CellConfig 2 }

powerRampStep OBJECT-TYPE
    SYNTAX Unsigned32 (1..8)
    ACCESS read-write
    STATUS optional
    DESCRIPTION "Power Ramp Step"
    ::= { sib5CellConfig 3 }

preambleRetransmissionMax OBJECT-TYPE
    SYNTAX Unsigned32 (1..64)
    ACCESS read-write
    STATUS optional
    DESCRIPTION "Max Number Preamble Re-transmissions"
    ::= { sib5CellConfig 4 }

-- SIB7

ulInterference OBJECT-TYPE
    SYNTAX INTEGER (-110..-70)
    ACCESS read-write
    STATUS optional
    DESCRIPTION "Uplink Interference (dBm)"
    ::= { sib7CellConfig 1 }

-- SIB11

hcsUsed OBJECT-TYPE
    SYNTAX Unsigned32 (0..1)
    ACCESS read-write
    STATUS optional
    DESCRIPTION "HCS Used"
    ::= { neighbourCellConfig 1 }

numInterRatNeighbourCells OBJECT-TYPE
    SYNTAX Unsigned32 (0..15)
    ACCESS read-write
    STATUS optional
    DESCRIPTION "Number of Inter-RAT (GSM) Neighbour Cells"
    ::= { neighbourCellConfig 4 }

--Per-Cell Settings

--
-- INTRA-FREQ NEIGHBOURS
--

-- Intra-Freq Neighbour Cell 1

rncId-a0 OBJECT-TYPE
    SYNTAX Unsigned32 (0..4096)
    ACCESS read-write
    STATUS optional
    DESCRIPTION "Intra-Freq Neighbour Cell 1 - RNC ID"
    ::= { intraCell0 2 }

scramblingCode-a0 OBJECT-TYPE
    SYNTAX Unsigned32 (0..511)
    ACCESS read-write
    STATUS optional
    DESCRIPTION "Intra-Freq Neighbour Cell 1 - Scrambling Code"
    ::= { intraCell0 5 }

hcs-PRIO-a0 OBJECT-TYPE
    SYNTAX Unsigned32 (0..7)
    ACCESS read-write
    STATUS optional
    DESCRIPTION "Intra-Freq Neighbour Cell 1 - HCS Priority"
    ::= { intraCell0 6 }

-- Intra-Freq Neighbour Cell 2

rncId-a1 OBJECT-TYPE
    SYNTAX Unsigned32 (0..4096)
    ACCESS read-write
    STATUS optional
    DESCRIPTION "Intra-Freq Neighbour Cell 2 - RNC ID"
    ::= { intraCell1 2 }

scramblingCode-a1 OBJECT-TYPE
    SYNTAX Unsigned32 (0..511)
    ACCESS read-write
    STATUS optional
    DESCRIPTION "Intra-Freq Neighbour Cell 2 - Scrambling Code"
    ::= { intraCell1 5 }

hcs-PRIO-a1 OBJECT-TYPE
    SYNTAX Unsigned32 (0..7)
    ACCESS read-write
    STATUS optional
    DESCRIPTION "Intra-Freq Neighbour Cell 2 - HCS Priority"
    ::= { intraCell1 6 }

-- Intra-Freq Neighbour Cell 3

rncId-a2 OBJECT-TYPE
    SYNTAX Unsigned32 (0..4096)
    ACCESS read-write
    STATUS optional
    DESCRIPTION "Intra-Freq Neighbour Cell 3 - RNC ID"
    ::= { intraCell2 2 }

scramblingCode-a2 OBJECT-TYPE
    SYNTAX Unsigned32 (0..511)
    ACCESS read-write
    STATUS optional
    DESCRIPTION "Intra-Freq Neighbour Cell 3 - Scrambling Code"
    ::= { intraCell2 5 }

hcs-PRIO-a2 OBJECT-TYPE
    SYNTAX Unsigned32 (0..7)
    ACCESS read-write
    STATUS optional
    DESCRIPTION "Intra-Freq Neighbour Cell 3 - HCS Priority"
    ::= { intraCell2 6 }

-- Intra-Freq Neighbour Cell 4

rncId-a3 OBJECT-TYPE
    SYNTAX Unsigned32 (0..4096)
    ACCESS read-write
    STATUS optional
    DESCRIPTION "Intra-Freq Neighbour Cell 4 - RNC ID"
    ::= { intraCell3 2 }

scramblingCode-a3 OBJECT-TYPE
    SYNTAX Unsigned32 (0..511)
    ACCESS read-write
    STATUS optional
    DESCRIPTION "Intra-Freq Neighbour Cell 4 - Scrambling Code"
    ::= { intraCell3 5 }

hcs-PRIO-a3 OBJECT-TYPE
    SYNTAX Unsigned32 (0..7)
    ACCESS read-write
    STATUS optional
    DESCRIPTION "Intra-Freq Neighbour Cell 4 - HCS Priority"
    ::= { intraCell3 6 }

-- Intra-Freq Neighbour Cell 5

rncId-a4 OBJECT-TYPE
    SYNTAX Unsigned32 (0..4096)
    ACCESS read-write
    STATUS optional
    DESCRIPTION "Intra-Freq Neighbour Cell 5 - RNC ID"
    ::= { intraCell4 2 }

scramblingCode-a4 OBJECT-TYPE
    SYNTAX Unsigned32 (0..511)
    ACCESS read-write
    STATUS optional
    DESCRIPTION "Intra-Freq Neighbour Cell 5 - Scrambling Code"
    ::= { intraCell4 5 }

hcs-PRIO-a4 OBJECT-TYPE
    SYNTAX Unsigned32 (0..7)
    ACCESS read-write
    STATUS optional
    DESCRIPTION "Intra-Freq Neighbour Cell 5 - HCS Priority"
    ::= { intraCell4 6 }

-- Intra-Freq Neighbour Cell 6

rncId-a5 OBJECT-TYPE
    SYNTAX Unsigned32 (0..4096)
    ACCESS read-write
    STATUS optional
    DESCRIPTION "Intra-Freq Neighbour Cell 6 - RNC ID"
    ::= { intraCell5 2 }

scramblingCode-a5 OBJECT-TYPE
    SYNTAX Unsigned32 (0..511)
    ACCESS read-write
    STATUS optional
    DESCRIPTION "Intra-Freq Neighbour Cell 6 - Scrambling Code"
    ::= { intraCell5 5 }

hcs-PRIO-a5 OBJECT-TYPE
    SYNTAX Unsigned32 (0..7)
    ACCESS read-write
    STATUS optional
    DESCRIPTION "Intra-Freq Neighbour Cell 6 - HCS Priority"
    ::= { intraCell5 6 }

--
-- INTER-FREQ NEIGHBOURS
--

-- Inter-Freq Neighbour Cell 1

rncId-e0 OBJECT-TYPE
    SYNTAX Unsigned32 (0..4096)
    ACCESS read-write
    STATUS optional
    DESCRIPTION "Inter-Freq Neighbour Cell 1 - RNC ID"
    ::= { interCell0 2 }

uarfcn-e0 OBJECT-TYPE
    SYNTAX Unsigned32 (412..10838)
    ACCESS read-write
    STATUS optional
    DESCRIPTION "Inter-Freq Neighbour Cell 1 - UARFCN"
    ::= { interCell0 5 }

scramblingCode-e0 OBJECT-TYPE
    SYNTAX Unsigned32 (0..511)
    ACCESS read-write
    STATUS optional
    DESCRIPTION "Inter-Freq Neighbour Cell 1 - Scrambling Code"
    ::= { interCell0 6 }

hcs-PRIO-e0 OBJECT-TYPE
    SYNTAX Unsigned32 (0..7)
    ACCESS read-write
    STATUS optional
    DESCRIPTION "Inter-Freq Neighbour Cell 1 - HCS Priority"
    ::= { interCell0 7 }

-- Inter-Freq Neighbour Cell 2

rncId-e1 OBJECT-TYPE
    SYNTAX Unsigned32 (0..4096)
    ACCESS read-write
    STATUS optional
    DESCRIPTION "Inter-Freq Neighbour Cell 2 - RNC ID"
    ::= { interCell1 2 }

uarfcn-e1 OBJECT-TYPE
    SYNTAX Unsigned32 (412..10838)
    ACCESS read-write
    STATUS optional
    DESCRIPTION "Inter-Freq Neighbour Cell 2 - ARFCN"
    ::= { interCell1 5 }

scramblingCode-e1 OBJECT-TYPE
    SYNTAX Unsigned32 (0..511)
    ACCESS read-write
    STATUS optional
    DESCRIPTION "Inter-Freq Neighbour Cell 2 - Scrambling Code"
    ::= { interCell1 6 }

hcs-PRIO-e1 OBJECT-TYPE
    SYNTAX Unsigned32 (0..7)
    ACCESS read-write
    STATUS optional
    DESCRIPTION "Inter-Freq Neighbour Cell 2 - HCS Priority"
    ::= { interCell1 7 }

-- Inter-Freq Neighbour Cell 3

rncId-e2 OBJECT-TYPE
    SYNTAX Unsigned32 (0..4096)
    ACCESS read-write
    STATUS optional
    DESCRIPTION "Inter-Freq Neighbour Cell 3 - RNC ID"
    ::= { interCell2 2 }

uarfcn-e2 OBJECT-TYPE
    SYNTAX Unsigned32 (412..10838)
    ACCESS read-write
    STATUS optional
    DESCRIPTION "Inter-Freq Neighbour Cell 3 - ARFCN"
    ::= { interCell2 5 }

scramblingCode-e2 OBJECT-TYPE
    SYNTAX Unsigned32 (0..511)
    ACCESS read-write
    STATUS optional
    DESCRIPTION "Inter-Freq Neighbour Cell 3 - Scrambling Code"
    ::= { interCell2 6 }

hcs-PRIO-e2 OBJECT-TYPE
    SYNTAX Unsigned32 (0..7)
    ACCESS read-write
    STATUS optional
    DESCRIPTION "Inter-Freq Neighbour Cell 3 - HCS Priority"
    ::= { interCell2 7 }

-- Inter-Freq Neighbour Cell 4

rncId-e3 OBJECT-TYPE
    SYNTAX Unsigned32 (0..4096)
    ACCESS read-write
    STATUS optional
    DESCRIPTION "Inter-Freq Neighbour Cell 4 - RNC ID"
    ::= { interCell3 2 }

uarfcn-e3 OBJECT-TYPE
    SYNTAX Unsigned32 (412..10838)
    ACCESS read-write
    STATUS optional
    DESCRIPTION "Inter-Freq Neighbour Cell 4 - ARFCN"
    ::= { interCell3 5 }

scramblingCode-e3 OBJECT-TYPE
    SYNTAX Unsigned32 (0..511)
    ACCESS read-write
    STATUS optional
    DESCRIPTION "Inter-Freq Neighbour Cell 4 - Scrambling Code"
    ::= { interCell3 6 }

hcs-PRIO-e3 OBJECT-TYPE
    SYNTAX Unsigned32 (0..7)
    ACCESS read-write
    STATUS optional
    DESCRIPTION "Inter-Freq Neighbour Cell 4 - HCS Priority"
    ::= { interCell3 7 }

-- Inter-Freq Neighbour Cell 5

rncId-e4 OBJECT-TYPE
    SYNTAX Unsigned32 (0..4096)
    ACCESS read-write
    STATUS optional
    DESCRIPTION "Inter-Freq Neighbour Cell 5 - RNC ID"
    ::= { interCell4 2 }

uarfcn-e4 OBJECT-TYPE
    SYNTAX Unsigned32 (412..10838)
    ACCESS read-write
    STATUS optional
    DESCRIPTION "Inter-Freq Neighbour Cell 5 - ARFCN"
    ::= { interCell4 5 }

scramblingCode-e4 OBJECT-TYPE
    SYNTAX Unsigned32 (0..511)
    ACCESS read-write
    STATUS optional
    DESCRIPTION "Inter-Freq Neighbour Cell 5 - Scrambling Code"
    ::= { interCell4 6 }

hcs-PRIO-e4 OBJECT-TYPE
    SYNTAX Unsigned32 (0..7)
    ACCESS read-write
    STATUS optional
    DESCRIPTION "Inter-Freq Neighbour Cell 5 - HCS Priority"
    ::= { interCell4 7 }

-- Inter-Freq Neighbour Cell 6

rncId-e5 OBJECT-TYPE
    SYNTAX Unsigned32 (0..4096)
    ACCESS read-write
    STATUS optional
    DESCRIPTION "Inter-Freq Neighbour Cell 6 - RNC ID"
    ::= { interCell5 2 }

uarfcn-e5 OBJECT-TYPE
    SYNTAX Unsigned32 (412..10838)
    ACCESS read-write
    STATUS optional
    DESCRIPTION "Inter-Freq Neighbour Cell 6 - ARFCN"
    ::= { interCell5 5 }

scramblingCode-e5 OBJECT-TYPE
    SYNTAX Unsigned32 (0..511)
    ACCESS read-write
    STATUS optional
    DESCRIPTION "Inter-Freq Neighbour Cell 6 - Scrambling Code"
    ::= { interCell5 6 }

hcs-PRIO-e5 OBJECT-TYPE
    SYNTAX Unsigned32 (0..7)
    ACCESS read-write
    STATUS optional
    DESCRIPTION "Inter-Freq Neighbour Cell 6 - HCS Priority"
    ::= { interCell5 7 }

--
-- INTER-RAT NEIGHBOURS
--

-- Inter-RAT (GSM) Neighbour Cell 1

arfcn-r0 OBJECT-TYPE
    SYNTAX Unsigned32 (0..1023)
    ACCESS read-write
    STATUS optional
    DESCRIPTION "Inter-RAT (GSM) Neighbour Cell 1 - ARFCN"
    ::= { interRatCell0 2 }

bcc-r0 OBJECT-TYPE
    SYNTAX Unsigned32 (0..7)
    ACCESS read-write
    STATUS optional
    DESCRIPTION "Inter-RAT (GSM) Neighbour Cell 1 - BCC"
    ::= { interRatCell0 3 }

ncc-r0 OBJECT-TYPE
    SYNTAX Unsigned32 (0..7)
    ACCESS read-write
    STATUS optional
    DESCRIPTION "Inter-RAT (GSM) Neighbour Cell 1 - NCC"
    ::= { interRatCell0 4 }

isPcs-r0 OBJECT-TYPE
    SYNTAX Unsigned32 (0..1)
    ACCESS read-write
    STATUS optional
    DESCRIPTION "Inter-RAT (GSM) Neighbour Cell 1 - PCS(1)/DCS(0)"
    ::= { interRatCell0 8 }

-- Inter-RAT (GSM) Neighbour Cell 2

arfcn-r1 OBJECT-TYPE
    SYNTAX Unsigned32 (0..1023)
    ACCESS read-write
    STATUS optional
    DESCRIPTION "Inter-RAT (GSM) Neighbour Cell 2 - ARFCN"
    ::= { interRatCell1 2 }

bcc-r1 OBJECT-TYPE
    SYNTAX Unsigned32 (0..7)
    ACCESS read-write
    STATUS optional
    DESCRIPTION "Inter-RAT (GSM) Neighbour Cell 2 - BCC"
    ::= { interRatCell1 3 }

ncc-r1 OBJECT-TYPE
    SYNTAX Unsigned32 (0..7)
    ACCESS read-write
    STATUS optional
    DESCRIPTION "Inter-RAT (GSM) Neighbour Cell 2 - NCC"
    ::= { interRatCell1 4 }

isPcs-r1 OBJECT-TYPE
    SYNTAX Unsigned32 (0..1)
    ACCESS read-write
    STATUS optional
    DESCRIPTION "Inter-RAT (GSM) Neighbour Cell 2 - PCS(1)/DCS(0)"
    ::= { interRatCell1 8 }

-- Inter-RAT (GSM) Neighbour Cell 3

arfcn-r2 OBJECT-TYPE
    SYNTAX Unsigned32 (0..1023)
    ACCESS read-write
    STATUS optional
    DESCRIPTION "Inter-RAT (GSM) Neighbour Cell 3 - ARFCN"
    ::= { interRatCell2 2 }

bcc-r2 OBJECT-TYPE
    SYNTAX Unsigned32 (0..7)
    ACCESS read-write
    STATUS optional
    DESCRIPTION "Inter-RAT (GSM) Neighbour Cell 3 - BCC"
    ::= { interRatCell2 3 }

ncc-r2 OBJECT-TYPE
    SYNTAX Unsigned32 (0..7)
    ACCESS read-write
    STATUS optional
    DESCRIPTION "Inter-RAT (GSM) Neighbour Cell 3 - NCC"
    ::= { interRatCell2 4 }

isPcs-r2 OBJECT-TYPE
    SYNTAX Unsigned32 (0..1)
    ACCESS read-write
    STATUS optional
    DESCRIPTION "Inter-RAT (GSM) Neighbour Cell 3 - PCS(1)/DCS(0)"
    ::= { interRatCell2 8 }

-- Inter-RAT (GSM) Neighbour Cell 4

arfcn-r3 OBJECT-TYPE
    SYNTAX Unsigned32 (0..1023)
    ACCESS read-write
    STATUS optional
    DESCRIPTION "Inter-RAT (GSM) Neighbour Cell 4 - ARFCN"
    ::= { interRatCell3 2 }

bcc-r3 OBJECT-TYPE
    SYNTAX Unsigned32 (0..7)
    ACCESS read-write
    STATUS optional
    DESCRIPTION "Inter-RAT (GSM) Neighbour Cell 4 - BCC"
    ::= { interRatCell3 3 }

ncc-r3 OBJECT-TYPE
    SYNTAX Unsigned32 (0..7)
    ACCESS read-write
    STATUS optional
    DESCRIPTION "Inter-RAT (GSM) Neighbour Cell 4 - NCC"
    ::= { interRatCell3 4 }

isPcs-r3 OBJECT-TYPE
    SYNTAX Unsigned32 (0..1)
    ACCESS read-write
    STATUS optional
    DESCRIPTION "Inter-RAT (GSM) Neighbour Cell 4 - PCS(1)/DCS(0)"
    ::= { interRatCell3 8 }

-- Inter-RAT (GSM) Neighbour Cell 5

arfcn-r4 OBJECT-TYPE
    SYNTAX Unsigned32 (0..1023)
    ACCESS read-write
    STATUS optional
    DESCRIPTION "Inter-RAT (GSM) Neighbour Cell 5 - ARFCN"
    ::= { interRatCell4 2 }

bcc-r4 OBJECT-TYPE
    SYNTAX Unsigned32 (0..7)
    ACCESS read-write
    STATUS optional
    DESCRIPTION "Inter-RAT (GSM) Neighbour Cell 5 - BCC"
    ::= { interRatCell4 3 }

ncc-r4 OBJECT-TYPE
    SYNTAX Unsigned32 (0..7)
    ACCESS read-write
    STATUS optional
    DESCRIPTION "Inter-RAT (GSM) Neighbour Cell 5 - NCC"
    ::= { interRatCell4 4 }

isPcs-r4 OBJECT-TYPE
    SYNTAX Unsigned32 (0..1)
    ACCESS read-write
    STATUS optional
    DESCRIPTION "Inter-RAT (GSM) Neighbour Cell 5 - PCS(1)/DCS(0)"
    ::= { interRatCell4 8 }

-- Inter-RAT (GSM) Neighbour Cell 6

arfcn-r5 OBJECT-TYPE
    SYNTAX Unsigned32 (0..1023)
    ACCESS read-write
    STATUS optional
    DESCRIPTION "Inter-RAT (GSM) Neighbour Cell 6 - ARFCN"
    ::= { interRatCell5 2 }

bcc-r5 OBJECT-TYPE
    SYNTAX Unsigned32 (0..7)
    ACCESS read-write
    STATUS optional
    DESCRIPTION "Inter-RAT (GSM) Neighbour Cell 6 - BCC"
    ::= { interRatCell5 3 }

ncc-r5 OBJECT-TYPE
    SYNTAX Unsigned32 (0..7)
    ACCESS read-write
    STATUS optional
    DESCRIPTION "Inter-RAT (GSM) Neighbour Cell 6 - NCC"
    ::= { interRatCell5 4 }

isPcs-r5 OBJECT-TYPE
    SYNTAX Unsigned32 (0..1)
    ACCESS read-write
    STATUS optional
    DESCRIPTION "Inter-RAT (GSM) Neighbour Cell 6 - PCS(1)/DCS(0)"
    ::= { interRatCell5 8 }

--Management

reboot OBJECT-TYPE
    SYNTAX Unsigned32 (1..1)
    ACCESS read-write
    STATUS optional
    DESCRIPTION "Write 1 to reboot unit."
    ::= { management 2 }

sendTestTrap OBJECT-TYPE
    SYNTAX Unsigned32 (1..1)
    ACCESS read-write
    STATUS optional
    DESCRIPTION "Write 1 to cause unit to send a test trap."
    ::= { management 3 }

fapAdminState OBJECT-TYPE
    SYNTAX Unsigned32 (0..1)
    ACCESS read-write
    STATUS optional
    DESCRIPTION "0 = FAP locked (RF off, Iu down), 1 = FAP unlocked (RF on if Iu up)."
    ::= { management 4 }

fapOpState OBJECT-TYPE
    SYNTAX Unsigned32 (0..1)
    ACCESS read-write
    STATUS optional
    DESCRIPTION "0 = FAP disabled (RF off), 1 = FAP enabled (RF on)."
    ::= { management 5 }    

enableTr069 OBJECT-TYPE
    SYNTAX Unsigned32 (0..1)
    ACCESS read-write
    STATUS optional
    DESCRIPTION "0 = TR069 disabled, 1 = TR069 enabled."
    ::= { tr069 1 }

primaryConfigurationServer OBJECT-TYPE
    SYNTAX OCTET STRING (SIZE(0..80))
    ACCESS read-write
    STATUS optional
    DESCRIPTION "IP Address/URL for the Primary Configuration Server."
    ::= { configurationServer 1 }

secondaryConfigurationServer OBJECT-TYPE
    SYNTAX OCTET STRING (SIZE(0..80))
    ACCESS read-write
    STATUS optional
    DESCRIPTION "IP Address/URL for the Secondary Configuration Server."
    ::= { configurationServer 2 }

tertiaryConfigurationServer OBJECT-TYPE
    SYNTAX OCTET STRING (SIZE(0..80))
    ACCESS read-write
    STATUS optional
    DESCRIPTION "IP Address/URL for the Tertiary Configuration Server."
    ::= { configurationServer 3 }

kpiReportDuration OBJECT-TYPE
    SYNTAX Unsigned32 (5..1440)
    ACCESS read-write
    STATUS optional
    DESCRIPTION "Duration covered by a KPI Report (in minutes)."
    ::= { tr069 4 }

sctp1stLocalPort OBJECT-TYPE
    SYNTAX Unsigned32 (0..65535)
    ACCESS read-write
    STATUS optional
    DESCRIPTION "SCTP local port number used for odd FAP inner ip addresses."
    ::= { tr069 5 }

sctp2ndLocalPort OBJECT-TYPE
    SYNTAX Unsigned32 (0..65535)
    ACCESS read-write
    STATUS optional
    DESCRIPTION "SCTP local port number used for even FAP inner ip addresses."
    ::= { tr069 6 }

sctp1stRemotePort OBJECT-TYPE
    SYNTAX Unsigned32 (0..65535)
    ACCESS read-write
    STATUS optional
    DESCRIPTION "SCTP remote port number used for odd FAP inner ip addresses."
    ::= { tr069 7}

sctp2ndRemotePort OBJECT-TYPE
    SYNTAX Unsigned32 (0..65535)
    ACCESS read-write
    STATUS optional
    DESCRIPTION "SCTP remote port number used for even FAP inner ip addresses."
    ::= { tr069 8 }

enableHandoverToMacro OBJECT-TYPE
    SYNTAX Unsigned32 (0..1)
    ACCESS read-write
    STATUS optional
    DESCRIPTION "0 = Handover (Relocation) Disabled, 1 = Handover (Relocation) Enabled."
    ::= { licensing 1 }

enableHsdpa5Codes OBJECT-TYPE
    SYNTAX Unsigned32 (0..1)
    ACCESS read-write
    STATUS optional
    DESCRIPTION "0 = HSDPA 3.6Mbit disabled, 1 = HSDPA 3.6Mbit enabled."
    ::= { licensing 2 }

enableHsdpa10Codes OBJECT-TYPE
    SYNTAX Unsigned32 (0..1)
    ACCESS read-write
    STATUS optional
    DESCRIPTION "0 = HSDPA 7.2Mbit disabled, 1 = HSDPA 7.2Mbit enabled."
    ::= { licensing 3 }

enableHsupa OBJECT-TYPE
    SYNTAX Unsigned32 (0..1)
    ACCESS read-write
    STATUS optional
    DESCRIPTION "0 = HSUPA disabled, 1 = HSUPA enabled."
    ::= { licensing 4 }

udpLogDestIpAddress OBJECT-TYPE
    SYNTAX Unsigned32
    ACCESS read-write
    STATUS optional
    DESCRIPTION "No longer supported via SNMP.  Use nas-system-configuration."
    ::= { ipSettings 1 }

unitIpAddress OBJECT-TYPE
    SYNTAX IpAddress
    ACCESS read-write
    STATUS optional
    DESCRIPTION "Unit IP Address.  Will be stored in flash
                 but requires reboot to take effect."
    ::= { ipSettings 2 }

unitIpNetMask OBJECT-TYPE
    SYNTAX IpAddress
    ACCESS read-write
    STATUS optional
    DESCRIPTION "Unit IP Net Mask.  Will be stored in flash
                 but requires reboot to take effect."
    ::= { ipSettings 3 }

unitIpRoute OBJECT-TYPE
    SYNTAX IpAddress
    ACCESS read-write
    STATUS optional
    DESCRIPTION "Unused."
    ::= { ipSettings 4 }

unitIpGateway OBJECT-TYPE
    SYNTAX IpAddress
    ACCESS read-write
    STATUS optional
    DESCRIPTION "Unit IP Gateway.  Will be stored in flash
                 but requires reboot to take effect."
    ::= { ipSettings 5 }
    
unitIpPathMtuDiscovery OBJECT-TYPE
    SYNTAX Unsigned32 (0..1)
    ACCESS read-write
    STATUS optional
    DESCRIPTION "Unit IP Path Mtu Discovery. Note: requires
    			reboot! Enable with 1, Disable with 0"
    ::= { ipSettings 6 }

unitIpFirewallEnable OBJECT-TYPE
    SYNTAX Unsigned32 (0..1)
    ACCESS read-write
    STATUS optional
    DESCRIPTION "0 = Firewall disabled, 1 = Firewall enabled."
    ::= { ipSettings 7 }

-- ike := ipSettings 8
-- qos := ipSettings 9

ikeIPsecEnable OBJECT-TYPE
    SYNTAX Unsigned32 (0..1)
    ACCESS read-write
    STATUS optional
    DESCRIPTION "0 = IpSec disabled, 1 = IpSec enabled."
    ::= { ike 1 }

ikeIPsecGwAddr OBJECT-TYPE
    SYNTAX IpAddress
    ACCESS read-write
    STATUS optional
    DESCRIPTION "IP Address of the IPsec Gateway to reach the core network."
    ::= { ike 2 }

qosEnable OBJECT-TYPE
    SYNTAX Unsigned32 (0..1)
    ACCESS read-write
    STATUS optional
    DESCRIPTION "Enabling QoS =1; Disabling = 0"
    ::= { qos 1 }

fap_cir OBJECT-TYPE
    SYNTAX OCTET STRING
    ACCESS read-write
    STATUS optional
    DESCRIPTION "Rate: Megabits are indicated adding postifix 'Mbit'; or bps just with number (ex: 1Mbit or 1000000)"
    ::= { qos 3 }


pppoeEnabled OBJECT-TYPE
    SYNTAX Unsigned32 (0..1)
    ACCESS read-write
    STATUS optional
    DESCRIPTION "Enable PPPoE mode. Requires reboot to take effect."
    ::= { pppoeParams 1 }

pppoeUser OBJECT-TYPE
    SYNTAX OCTET STRING (SIZE(0..255))
    ACCESS read-write
    STATUS optional
    DESCRIPTION "PPPoE user name. Requires reboot to take effect."
    ::= { pppoeParams 2 }

pppoePassword OBJECT-TYPE
    SYNTAX OCTET STRING (SIZE(0..255))
    ACCESS read-write
    STATUS optional
    DESCRIPTION "PPPoE password. Requires reboot to take effect."
    ::= { pppoeParams 3 }

pppoeServiceName OBJECT-TYPE
    SYNTAX OCTET STRING (SIZE(0..255))
    ACCESS read-write
    STATUS optional
    DESCRIPTION "PPPoE service to request. Typically, this is set to ''
                 to signify ANY service. Usually, PPPoE servers provide
                 just a single service and setting it to ANY suffices.
                 However, some servers expect to receive a specific
                 service name. Requires reboot to take effect."
    ::= { pppoeParams 4 }    
    
--config   

gsmRssiThresholdDbm OBJECT-TYPE
    SYNTAX Signed32 (-130..0)
    ACCESS read-write
    STATUS optional
    DESCRIPTION "Lower limit to GSM-REM scan reporting"
    ::= { remScanConfig 1 }         
    
--freqScanConfig    
 
freqCalEnable OBJECT-TYPE
    SYNTAX Unsigned32 (0..1)
    ACCESS read-write
    STATUS optional
    DESCRIPTION "1 = start frequency cal rem scan."
    ::= { freqScanConfig 1 }
      
freqCalTimeoutSecs OBJECT-TYPE
    SYNTAX Unsigned32 (0..3600)
    ACCESS read-write
    STATUS optional
    DESCRIPTION "Timeout for freq cal scan"
    ::= { freqScanConfig 2 } 
    
--ncScanConfig

ncScanEnable OBJECT-TYPE
    SYNTAX Unsigned32 (0..1)
    ACCESS read-write
    STATUS optional
    DESCRIPTION "1 = start neighbour cell rem scan."
    ::= { ncScanConfig 1 }
    
ncNumWcdmaUArfcnsToScan OBJECT-TYPE
    SYNTAX Unsigned32 (1..4)
    ACCESS read-write
    STATUS optional
    DESCRIPTION "Number of UARFCNs to scan."
    ::= { ncScanConfig 2 }
        
ncWcdmaUarfcn0 OBJECT-TYPE
    SYNTAX Unsigned32 (412..10838)
    ACCESS read-write
    STATUS optional
    DESCRIPTION "First UArfcn to scan"
    ::= { ncScanConfig 3 }

ncWcdmaUarfcn1 OBJECT-TYPE
    SYNTAX Unsigned32 (412..10838)
    ACCESS read-write
    STATUS optional
    DESCRIPTION "Second UArfcn to scan"
    ::= { ncScanConfig 4 }

ncWcdmaUarfcn2 OBJECT-TYPE
    SYNTAX Unsigned32 (412..10838)
    ACCESS read-write
    STATUS optional
    DESCRIPTION "Third UArfcn to scan"
    ::= { ncScanConfig 5 }

ncWcdmaUarfcn3 OBJECT-TYPE
    SYNTAX Unsigned32 (412..10838)
    ACCESS read-write
    STATUS optional
    DESCRIPTION "Fourth UArfcn to scan"
    ::= { ncScanConfig 6 }      
    
ncGsmArfcn0 OBJECT-TYPE
    SYNTAX Unsigned32 (0..1023)
    ACCESS read-write
    STATUS optional
    DESCRIPTION "REM scan any non pcs gsm arfcn 0."
    ::= { ncScanConfig 8 }

ncGsmArfcn1 OBJECT-TYPE
    SYNTAX Unsigned32 (0..1023)
    ACCESS read-write
    STATUS optional
    DESCRIPTION "REM scan any non pcs gsm arfcn 1."
    ::= { ncScanConfig 9 }

ncGsmArfcn2 OBJECT-TYPE
    SYNTAX Unsigned32 (0..1023)
    ACCESS read-write
    STATUS optional
    DESCRIPTION "REM scan any non pcs gsm arfcn 2."
    ::= { ncScanConfig 10 }

ncGsmArfcn3 OBJECT-TYPE
    SYNTAX Unsigned32 (0..1023)
    ACCESS read-write
    STATUS optional
    DESCRIPTION "REM scan any non pcs gsm arfcn 3."
    ::= { ncScanConfig 11 }

ncGsmArfcn4 OBJECT-TYPE
    SYNTAX Unsigned32 (0..1023)
    ACCESS read-write
    STATUS optional
    DESCRIPTION "REM scan any non pcs gsm arfcn 4."
    ::= { ncScanConfig 12 }

ncGsmArfcn5 OBJECT-TYPE
    SYNTAX Unsigned32 (0..1023)
    ACCESS read-write
    STATUS optional
    DESCRIPTION "REM scan any non pcs gsm arfcn 5."
    ::= { ncScanConfig 13 }    
    
ncPcsArfcn0 OBJECT-TYPE
    SYNTAX Unsigned32 (512..810)
    ACCESS read-write
    STATUS optional
    DESCRIPTION "REM scan for pcs only arfcn 0."
    ::= { ncScanConfig 14 }

ncPcsArfcn1 OBJECT-TYPE
    SYNTAX Unsigned32 (512..810)
    ACCESS read-write
    STATUS optional
    DESCRIPTION "REM scan for pcs only arfcn 1."
    ::= { ncScanConfig 15 }

ncPcsArfcn2 OBJECT-TYPE
    SYNTAX Unsigned32 (512..810)
    ACCESS read-write
    STATUS optional
    DESCRIPTION "REM scan for pcs only arfcn 2."
    ::= { ncScanConfig 16 }

ncPcsArfcn3 OBJECT-TYPE
    SYNTAX Unsigned32 (512..810)
    ACCESS read-write
    STATUS optional
    DESCRIPTION "REM scan for pcs only arfcn 3."
    ::= { ncScanConfig 17 }

ncPcsArfcn4 OBJECT-TYPE
    SYNTAX Unsigned32 (512..810)
    ACCESS read-write
    STATUS optional
    DESCRIPTION "REM scan for pcs only arfcn 4."
    ::= { ncScanConfig 18 }

ncPcsArfcn5 OBJECT-TYPE
    SYNTAX Unsigned32 (512..810)
    ACCESS read-write
    STATUS optional
    DESCRIPTION "REM scan for pcs only arfcn 5."
    ::= { ncScanConfig 19 } 
    
ncScanTimeoutSecs OBJECT-TYPE
    SYNTAX Unsigned32 (0..3600)
    ACCESS read-write
    STATUS optional
    DESCRIPTION "Timeout for nc scan"
    ::= { ncScanConfig 20 } 
        
--status
        
remScanState OBJECT-TYPE
    SYNTAX Unsigned32 (0..1)
    ACCESS read-write
    STATUS optional
    DESCRIPTION "0 = idle, 1 = running"
    ::= { remScanStatus 1 }           
    
--freqScanResults

freqCalResult OBJECT-TYPE
    SYNTAX Unsigned32 (0..2)
    ACCESS read-write
    STATUS optional
    DESCRIPTION "0 = no configuration, 1 = no suitable cells found, 2 = calibrated"
    ::= { freqScanResults 1 } 
    
freqCalOffset OBJECT-TYPE
    SYNTAX Signed32 (-2147483647..2147483648)
    ACCESS read-write
    STATUS optional
    DESCRIPTION "Offset in Hz determined by previous scan. 0x80000000 if no value available."
    ::= { freqScanResults 2 } 
    
--ncScanResults

ncScanResult OBJECT-TYPE
    SYNTAX Unsigned32 (0..2)
    ACCESS read-write
    STATUS optional
    DESCRIPTION "0 = no configuration, 1 = no suitable cells found, 2 = scan complete"
    ::= { ncScanResults 1 } 

numInterRatNCellsFound OBJECT-TYPE
    SYNTAX Unsigned32 (0..15)
    ACCESS read-write
    STATUS optional
    DESCRIPTION "Number of Inter-RAT (GSM) Neighbour Cells"
    ::= { ncScanResults 4 }

--Per-Cell Settings

--
-- INTRA-FREQ NEIGHBOURS
--

-- Intra-Freq Neighbour Cell 1

ncScanCellId-a0 OBJECT-TYPE
    SYNTAX Unsigned32 (0..65535)
    ACCESS read-write
    STATUS optional
    DESCRIPTION "Intra-Freq Neighbour Cell 1 - Cell ID"
    ::= { ncScanIntraCell0 1 }

ncScanMcc-a0 OBJECT-TYPE
    SYNTAX Unsigned32 (0..65535)
    ACCESS read-write
    STATUS optional
    DESCRIPTION "Intra-Freq Neighbour Cell 1 - MCC"
    ::= { ncScanIntraCell0 2 }

ncScanMnc-a0 OBJECT-TYPE
    SYNTAX Unsigned32 (0..65535)
    ACCESS read-write
    STATUS optional
    DESCRIPTION "Intra-Freq Neighbour Cell 1 - MNC"
    ::= { ncScanIntraCell0 3 }

ncScanLac-a0 OBJECT-TYPE
    SYNTAX Unsigned32 (0..65535)
    ACCESS read-write
    STATUS optional
    DESCRIPTION "Intra-Freq Neighbour Cell 1 - LAC"
    ::= { ncScanIntraCell0 4 }

ncScanRac-a0 OBJECT-TYPE
    SYNTAX Unsigned32 (0..65535)
    ACCESS read-write
    STATUS optional
    DESCRIPTION "Intra-Freq Neighbour Cell 1 - RAC"
    ::= { ncScanIntraCell0 5 }

ncScanScramblingCode-a0 OBJECT-TYPE
    SYNTAX Unsigned32 (0..511)
    ACCESS read-write
    STATUS optional
    DESCRIPTION "Intra-Freq Neighbour Cell 1 - Scrambling Code"
    ::= { ncScanIntraCell0 6 }

ncScanSib11-a0 OBJECT-TYPE
    SYNTAX OCTET STRING (SIZE(0..255))
    ACCESS read-write
    STATUS optional
    DESCRIPTION "Intra-Freq Neighbour Cell 1 - SIB11 decode string"
    ::= { ncScanIntraCell0 7 } 
    
-- Intra-Freq Neighbour Cell 2

ncScanCellId-a1 OBJECT-TYPE
    SYNTAX Unsigned32 (0..65535)
    ACCESS read-write
    STATUS optional
    DESCRIPTION "Intra-Freq Neighbour Cell 2 - Cell ID"
    ::= { ncScanIntraCell1 1 }

ncScanMcc-a1 OBJECT-TYPE
    SYNTAX Unsigned32 (0..65535)
    ACCESS read-write
    STATUS optional
    DESCRIPTION "Intra-Freq Neighbour Cell 2 - MCC"
    ::= { ncScanIntraCell1 2 }

ncScanMnc-a1 OBJECT-TYPE
    SYNTAX Unsigned32 (0..65535)
    ACCESS read-write
    STATUS optional
    DESCRIPTION "Intra-Freq Neighbour Cell 2 - MNC"
    ::= { ncScanIntraCell1 3 }

ncScanLac-a1 OBJECT-TYPE
    SYNTAX Unsigned32 (0..65535)
    ACCESS read-write
    STATUS optional
    DESCRIPTION "Intra-Freq Neighbour Cell 2 - LAC"
    ::= { ncScanIntraCell1 4 }

ncScanRac-a1 OBJECT-TYPE
    SYNTAX Unsigned32 (0..65535)
    ACCESS read-write
    STATUS optional
    DESCRIPTION "Intra-Freq Neighbour Cell 2 - RAC"
    ::= { ncScanIntraCell1 5 }

ncScanScramblingCode-a1 OBJECT-TYPE
    SYNTAX Unsigned32 (0..511)
    ACCESS read-write
    STATUS optional
    DESCRIPTION "Intra-Freq Neighbour Cell 2 - Scrambling Code"
    ::= { ncScanIntraCell1 6 }

ncScanSib11-a1 OBJECT-TYPE
    SYNTAX OCTET STRING (SIZE(0..255))
    ACCESS read-write
    STATUS optional
    DESCRIPTION "Intra-Freq Neighbour Cell 2 - SIB11 decode string"
    ::= { ncScanIntraCell1 7 }     

-- Intra-Freq Neighbour Cell 3

ncScanCellId-a2 OBJECT-TYPE
    SYNTAX Unsigned32 (0..65535)
    ACCESS read-write
    STATUS optional
    DESCRIPTION "Intra-Freq Neighbour Cell 3 - Cell ID"
    ::= { ncScanIntraCell2 1 }

ncScanMcc-a2 OBJECT-TYPE
    SYNTAX Unsigned32 (0..65535)
    ACCESS read-write
    STATUS optional
    DESCRIPTION "Intra-Freq Neighbour Cell 3 - MCC"
    ::= { ncScanIntraCell2 2 }

ncScanMnc-a2 OBJECT-TYPE
    SYNTAX Unsigned32 (0..65535)
    ACCESS read-write
    STATUS optional
    DESCRIPTION "Intra-Freq Neighbour Cell 3 - MNC"
    ::= { ncScanIntraCell2 3 }

ncScanLac-a2 OBJECT-TYPE
    SYNTAX Unsigned32 (0..65535)
    ACCESS read-write
    STATUS optional
    DESCRIPTION "Intra-Freq Neighbour Cell 3 - LAC"
    ::= { ncScanIntraCell2 4 }

ncScanRac-a2 OBJECT-TYPE
    SYNTAX Unsigned32 (0..65535)
    ACCESS read-write
    STATUS optional
    DESCRIPTION "Intra-Freq Neighbour Cell 3 - RAC"
    ::= { ncScanIntraCell2 5 }

ncScanScramblingCode-a2 OBJECT-TYPE
    SYNTAX Unsigned32 (0..511)
    ACCESS read-write
    STATUS optional
    DESCRIPTION "Intra-Freq Neighbour Cell 3 - Scrambling Code"
    ::= { ncScanIntraCell2 6 }

ncScanSib11-a2 OBJECT-TYPE
    SYNTAX OCTET STRING (SIZE(0..255))
    ACCESS read-write
    STATUS optional
    DESCRIPTION "Intra-Freq Neighbour Cell 3 - SIB11 decode string"
    ::= { ncScanIntraCell2 7 }     

-- Intra-Freq Neighbour Cell 4

ncScanCellId-a3 OBJECT-TYPE
    SYNTAX Unsigned32 (0..65535)
    ACCESS read-write
    STATUS optional
    DESCRIPTION "Intra-Freq Neighbour Cell 4 - Cell ID"
    ::= { ncScanIntraCell3 1 }

ncScanMcc-a3 OBJECT-TYPE
    SYNTAX Unsigned32 (0..65535)
    ACCESS read-write
    STATUS optional
    DESCRIPTION "Intra-Freq Neighbour Cell 4 - MCC"
    ::= { ncScanIntraCell3 2 }

ncScanMnc-a3 OBJECT-TYPE
    SYNTAX Unsigned32 (0..65535)
    ACCESS read-write
    STATUS optional
    DESCRIPTION "Intra-Freq Neighbour Cell 4 - MNC"
    ::= { ncScanIntraCell3 3 }

ncScanLac-a3 OBJECT-TYPE
    SYNTAX Unsigned32 (0..65535)
    ACCESS read-write
    STATUS optional
    DESCRIPTION "Intra-Freq Neighbour Cell 4 - LAC"
    ::= { ncScanIntraCell3 4 }

ncScanRac-a3 OBJECT-TYPE
    SYNTAX Unsigned32 (0..65535)
    ACCESS read-write
    STATUS optional
    DESCRIPTION "Intra-Freq Neighbour Cell 4 - RAC"
    ::= { ncScanIntraCell3 5 }

ncScanScramblingCode-a3 OBJECT-TYPE
    SYNTAX Unsigned32 (0..511)
    ACCESS read-write
    STATUS optional
    DESCRIPTION "Intra-Freq Neighbour Cell 4 - Scrambling Code"
    ::= { ncScanIntraCell3 6 }

ncScanSib11-a3 OBJECT-TYPE
    SYNTAX OCTET STRING (SIZE(0..255))
    ACCESS read-write
    STATUS optional
    DESCRIPTION "Intra-Freq Neighbour Cell 4 - SIB11 decode string"
    ::= { ncScanIntraCell3 7 }     

-- Intra-Freq Neighbour Cell 5

ncScanCellId-a4 OBJECT-TYPE
    SYNTAX Unsigned32 (0..65535)
    ACCESS read-write
    STATUS optional
    DESCRIPTION "Intra-Freq Neighbour Cell 5 - Cell ID"
    ::= { ncScanIntraCell4 1 }

ncScanMcc-a4 OBJECT-TYPE
    SYNTAX Unsigned32 (0..65535)
    ACCESS read-write
    STATUS optional
    DESCRIPTION "Intra-Freq Neighbour Cell 5 - MCC"
    ::= { ncScanIntraCell4 2 }

ncScanMnc-a4 OBJECT-TYPE
    SYNTAX Unsigned32 (0..65535)
    ACCESS read-write
    STATUS optional
    DESCRIPTION "Intra-Freq Neighbour Cell 5 - MNC"
    ::= { ncScanIntraCell4 3 }

ncScanLac-a4 OBJECT-TYPE
    SYNTAX Unsigned32 (0..65535)
    ACCESS read-write
    STATUS optional
    DESCRIPTION "Intra-Freq Neighbour Cell 5 - LAC"
    ::= { ncScanIntraCell4 4 }

ncScanRac-a4 OBJECT-TYPE
    SYNTAX Unsigned32 (0..65535)
    ACCESS read-write
    STATUS optional
    DESCRIPTION "Intra-Freq Neighbour Cell 5 - RAC"
    ::= { ncScanIntraCell4 5 }

ncScanScramblingCode-a4 OBJECT-TYPE
    SYNTAX Unsigned32 (0..511)
    ACCESS read-write
    STATUS optional
    DESCRIPTION "Intra-Freq Neighbour Cell 5 - Scrambling Code"
    ::= { ncScanIntraCell4 6 }

ncScanSib11-a4 OBJECT-TYPE
    SYNTAX OCTET STRING (SIZE(0..255))
    ACCESS read-write
    STATUS optional
    DESCRIPTION "Intra-Freq Neighbour Cell 5 - SIB11 decode string"
    ::= { ncScanIntraCell4 7 }     

-- Intra-Freq Neighbour Cell 6

ncScanCellId-a5 OBJECT-TYPE
    SYNTAX Unsigned32 (0..65535)
    ACCESS read-write
    STATUS optional
    DESCRIPTION "Intra-Freq Neighbour Cell 6 - Cell ID"
    ::= { ncScanIntraCell5 1 }

ncScanMcc-a5 OBJECT-TYPE
    SYNTAX Unsigned32 (0..65535)
    ACCESS read-write
    STATUS optional
    DESCRIPTION "Intra-Freq Neighbour Cell 6 - MCC"
    ::= { ncScanIntraCell5 2 }

ncScanMnc-a5 OBJECT-TYPE
    SYNTAX Unsigned32 (0..65535)
    ACCESS read-write
    STATUS optional
    DESCRIPTION "Intra-Freq Neighbour Cell 6 - MNC"
    ::= { ncScanIntraCell5 3 }

ncScanLac-a5 OBJECT-TYPE
    SYNTAX Unsigned32 (0..65535)
    ACCESS read-write
    STATUS optional
    DESCRIPTION "Intra-Freq Neighbour Cell 6 - LAC"
    ::= { ncScanIntraCell5 4 }

ncScanRac-a5 OBJECT-TYPE
    SYNTAX Unsigned32 (0..65535)
    ACCESS read-write
    STATUS optional
    DESCRIPTION "Intra-Freq Neighbour Cell 6 - RAC"
    ::= { ncScanIntraCell5 5 }

ncScanScramblingCode-a5 OBJECT-TYPE
    SYNTAX Unsigned32 (0..511)
    ACCESS read-write
    STATUS optional
    DESCRIPTION "Intra-Freq Neighbour Cell 6 - Scrambling Code"
    ::= { ncScanIntraCell5 6 }

ncScanSib11-a5 OBJECT-TYPE
    SYNTAX OCTET STRING (SIZE(0..255))
    ACCESS read-write
    STATUS optional
    DESCRIPTION "Intra-Freq Neighbour Cell 6 - SIB11 decode string"
    ::= { ncScanIntraCell5 7 }     

--
-- INTER-FREQ NEIGHBOURS
--

-- Inter-Freq Neighbour Cell 1

ncScanCellId-e0 OBJECT-TYPE
    SYNTAX Unsigned32 (0..65535)
    ACCESS read-write
    STATUS optional
    DESCRIPTION "Inter-Freq Neighbour Cell 1 - Cell ID"
    ::= { ncScanInterCell0 1 }

ncScanMcc-e0 OBJECT-TYPE
    SYNTAX Unsigned32 (0..65535)
    ACCESS read-write
    STATUS optional
    DESCRIPTION "Inter-Freq Neighbour Cell 1 - MCC"
    ::= { ncScanInterCell0 2 }

ncScanMnc-e0 OBJECT-TYPE
    SYNTAX Unsigned32 (0..65535)
    ACCESS read-write
    STATUS optional
    DESCRIPTION "Inter-Freq Neighbour Cell 1 - MNC"
    ::= { ncScanInterCell0 3 }

ncScanLac-e0 OBJECT-TYPE
    SYNTAX Unsigned32 (0..65535)
    ACCESS read-write
    STATUS optional
    DESCRIPTION "Inter-Freq Neighbour Cell 1 - LAC"
    ::= { ncScanInterCell0 4 }

ncScanRac-e0 OBJECT-TYPE
    SYNTAX Unsigned32 (0..65535)
    ACCESS read-write
    STATUS optional
    DESCRIPTION "Inter-Freq Neighbour Cell 1 - RAC"
    ::= { ncScanInterCell0 5 }

ncScanUarfcn-e0 OBJECT-TYPE
    SYNTAX Unsigned32 (412..10838)
    ACCESS read-write
    STATUS optional
    DESCRIPTION "Inter-Freq Neighbour Cell 1 - UARFCN"
    ::= { ncScanInterCell0 6 }

ncScanScramblingCode-e0 OBJECT-TYPE
    SYNTAX Unsigned32 (0..511)
    ACCESS read-write
    STATUS optional
    DESCRIPTION "Inter-Freq Neighbour Cell 1 - Scrambling Code"
    ::= { ncScanInterCell0 7 }

ncScanSib11-e0 OBJECT-TYPE
    SYNTAX OCTET STRING (SIZE(0..255))
    ACCESS read-write
    STATUS optional
    DESCRIPTION "Inter-Freq Neighbour Cell 1 - SIB11 decode string"
    ::= { ncScanInterCell0 8 }     

-- Inter-Freq Neighbour Cell 2

ncScanCellId-e1 OBJECT-TYPE
    SYNTAX Unsigned32 (0..65535)
    ACCESS read-write
    STATUS optional
    DESCRIPTION "Inter-Freq Neighbour Cell 2 - Cell ID"
    ::= { ncScanInterCell1 1 }

ncScanMcc-e1 OBJECT-TYPE
    SYNTAX Unsigned32 (0..65535)
    ACCESS read-write
    STATUS optional
    DESCRIPTION "Inter-Freq Neighbour Cell 2 - MCC"
    ::= { ncScanInterCell1 2 }

ncScanMnc-e1 OBJECT-TYPE
    SYNTAX Unsigned32 (0..65535)
    ACCESS read-write
    STATUS optional
    DESCRIPTION "Inter-Freq Neighbour Cell 2 - MNC"
    ::= { ncScanInterCell1 3 }

ncScanLac-e1 OBJECT-TYPE
    SYNTAX Unsigned32 (0..65535)
    ACCESS read-write
    STATUS optional
    DESCRIPTION "Inter-Freq Neighbour Cell 2 - LAC"
    ::= { ncScanInterCell1 4 }

ncScanRac-e1 OBJECT-TYPE
    SYNTAX Unsigned32 (0..65535)
    ACCESS read-write
    STATUS optional
    DESCRIPTION "Inter-Freq Neighbour Cell 2 - RAC"
    ::= { ncScanInterCell1 5 }

ncScanUarfcn-e1 OBJECT-TYPE
    SYNTAX Unsigned32 (412..10838)
    ACCESS read-write
    STATUS optional
    DESCRIPTION "Inter-Freq Neighbour Cell 2 - ARFCN"
    ::= { ncScanInterCell1 6 }

ncScanScramblingCode-e1 OBJECT-TYPE
    SYNTAX Unsigned32 (0..511)
    ACCESS read-write
    STATUS optional
    DESCRIPTION "Inter-Freq Neighbour Cell 2 - Scrambling Code"
    ::= { ncScanInterCell1 7 }

ncScanSib11-e1 OBJECT-TYPE
    SYNTAX OCTET STRING (SIZE(0..255))
    ACCESS read-write
    STATUS optional
    DESCRIPTION "Inter-Freq Neighbour Cell 2 - SIB11 decode string"
    ::= { ncScanInterCell1 8 }        

-- Inter-Freq Neighbour Cell 3

ncScanCellId-e2 OBJECT-TYPE
    SYNTAX Unsigned32 (0..65535)
    ACCESS read-write
    STATUS optional
    DESCRIPTION "Inter-Freq Neighbour Cell 3 - Cell ID"
    ::= { ncScanInterCell2 1 }

ncScanMcc-e2 OBJECT-TYPE
    SYNTAX Unsigned32 (0..65535)
    ACCESS read-write
    STATUS optional
    DESCRIPTION "Inter-Freq Neighbour Cell 3 - MCC"
    ::= { ncScanInterCell2 2 }

ncScanMnc-e2 OBJECT-TYPE
    SYNTAX Unsigned32 (0..65535)
    ACCESS read-write
    STATUS optional
    DESCRIPTION "Inter-Freq Neighbour Cell 3 - MNC"
    ::= { ncScanInterCell2 3 }

ncScanLac-e2 OBJECT-TYPE
    SYNTAX Unsigned32 (0..65535)
    ACCESS read-write
    STATUS optional
    DESCRIPTION "Inter-Freq Neighbour Cell 3 - LAC"
    ::= { ncScanInterCell2 4 }

ncScanRac-e2 OBJECT-TYPE
    SYNTAX Unsigned32 (0..65535)
    ACCESS read-write
    STATUS optional
    DESCRIPTION "Inter-Freq Neighbour Cell 3 - RAC"
    ::= { ncScanInterCell2 5 }

ncScanUarfcn-e2 OBJECT-TYPE
    SYNTAX Unsigned32 (412..10838)
    ACCESS read-write
    STATUS optional
    DESCRIPTION "Inter-Freq Neighbour Cell 3 - ARFCN"
    ::= { ncScanInterCell2 6 }

ncScanScramblingCode-e2 OBJECT-TYPE
    SYNTAX Unsigned32 (0..511)
    ACCESS read-write
    STATUS optional
    DESCRIPTION "Inter-Freq Neighbour Cell 3 - Scrambling Code"
    ::= { ncScanInterCell2 7 }

ncScanSib11-e2 OBJECT-TYPE
    SYNTAX OCTET STRING (SIZE(0..255))
    ACCESS read-write
    STATUS optional
    DESCRIPTION "Inter-Freq Neighbour Cell 3 - SIB11 decode string"
    ::= { ncScanInterCell2 8 }        

-- Inter-Freq Neighbour Cell 4

ncScanCellId-e3 OBJECT-TYPE
    SYNTAX Unsigned32 (0..65535)
    ACCESS read-write
    STATUS optional
    DESCRIPTION "Inter-Freq Neighbour Cell 4 - Cell ID"
    ::= { ncScanInterCell3 1 }

ncScanMcc-e3 OBJECT-TYPE
    SYNTAX Unsigned32 (0..65535)
    ACCESS read-write
    STATUS optional
    DESCRIPTION "Inter-Freq Neighbour Cell 4 - MCC"
    ::= { ncScanInterCell3 2 }

ncScanMnc-e3 OBJECT-TYPE
    SYNTAX Unsigned32 (0..65535)
    ACCESS read-write
    STATUS optional
    DESCRIPTION "Inter-Freq Neighbour Cell 4 - MNC"
    ::= { ncScanInterCell3 3 }

ncScanLac-e3 OBJECT-TYPE
    SYNTAX Unsigned32 (0..65535)
    ACCESS read-write
    STATUS optional
    DESCRIPTION "Inter-Freq Neighbour Cell 4 - LAC"
    ::= { ncScanInterCell3 4 }

ncScanRac-e3 OBJECT-TYPE
    SYNTAX Unsigned32 (0..65535)
    ACCESS read-write
    STATUS optional
    DESCRIPTION "Inter-Freq Neighbour Cell 4 - RAC"
    ::= { ncScanInterCell3 5 }

ncScanUarfcn-e3 OBJECT-TYPE
    SYNTAX Unsigned32 (412..10838)
    ACCESS read-write
    STATUS optional
    DESCRIPTION "Inter-Freq Neighbour Cell 4 - ARFCN"
    ::= { ncScanInterCell3 6 }

ncScanScramblingCode-e3 OBJECT-TYPE
    SYNTAX Unsigned32 (0..511)
    ACCESS read-write
    STATUS optional
    DESCRIPTION "Inter-Freq Neighbour Cell 4 - Scrambling Code"
    ::= { ncScanInterCell3 7 }

ncScanSib11-e3 OBJECT-TYPE
    SYNTAX OCTET STRING (SIZE(0..255))
    ACCESS read-write
    STATUS optional
    DESCRIPTION "Inter-Freq Neighbour Cell 4 - SIB11 decode string"
    ::= { ncScanInterCell3 8 }        

-- Inter-Freq Neighbour Cell 5

ncScanCellId-e4 OBJECT-TYPE
    SYNTAX Unsigned32 (0..65535)
    ACCESS read-write
    STATUS optional
    DESCRIPTION "Inter-Freq Neighbour Cell 5 - Cell ID"
    ::= { ncScanInterCell4 1 }

ncScanMcc-e4 OBJECT-TYPE
    SYNTAX Unsigned32 (0..65535)
    ACCESS read-write
    STATUS optional
    DESCRIPTION "Inter-Freq Neighbour Cell 5 - MCC"
    ::= { ncScanInterCell4 2 }

ncScanMnc-e4 OBJECT-TYPE
    SYNTAX Unsigned32 (0..65535)
    ACCESS read-write
    STATUS optional
    DESCRIPTION "Inter-Freq Neighbour Cell 5 - MNC"
    ::= { ncScanInterCell4 3 }

ncScanLac-e4 OBJECT-TYPE
    SYNTAX Unsigned32 (0..65535)
    ACCESS read-write
    STATUS optional
    DESCRIPTION "Inter-Freq Neighbour Cell 5 - LAC"
    ::= { ncScanInterCell4 4 }

ncScanRac-e4 OBJECT-TYPE
    SYNTAX Unsigned32 (0..65535)
    ACCESS read-write
    STATUS optional
    DESCRIPTION "Inter-Freq Neighbour Cell 5 - RAC"
    ::= { ncScanInterCell4 5 }

ncScanUarfcn-e4 OBJECT-TYPE
    SYNTAX Unsigned32 (412..10838)
    ACCESS read-write
    STATUS optional
    DESCRIPTION "Inter-Freq Neighbour Cell 5 - ARFCN"
    ::= { ncScanInterCell4 6 }

ncScanScramblingCode-e4 OBJECT-TYPE
    SYNTAX Unsigned32 (0..511)
    ACCESS read-write
    STATUS optional
    DESCRIPTION "Inter-Freq Neighbour Cell 5 - Scrambling Code"
    ::= { ncScanInterCell4 7 }

ncScanSib11-e4 OBJECT-TYPE
    SYNTAX OCTET STRING (SIZE(0..255))
    ACCESS read-write
    STATUS optional
    DESCRIPTION "Inter-Freq Neighbour Cell 5 - SIB11 decode string"
    ::= { ncScanInterCell4 8 }        

-- Inter-Freq Neighbour Cell 6

ncScanCellId-e5 OBJECT-TYPE
    SYNTAX Unsigned32 (0..65535)
    ACCESS read-write
    STATUS optional
    DESCRIPTION "Inter-Freq Neighbour Cell 6 - Cell ID"
    ::= { ncScanInterCell5 1 }

ncScanMcc-e5 OBJECT-TYPE
    SYNTAX Unsigned32 (0..65535)
    ACCESS read-write
    STATUS optional
    DESCRIPTION "Inter-Freq Neighbour Cell 6 - MCC"
    ::= { ncScanInterCell5 2 }

ncScanMnc-e5 OBJECT-TYPE
    SYNTAX Unsigned32 (0..65535)
    ACCESS read-write
    STATUS optional
    DESCRIPTION "Inter-Freq Neighbour Cell 6 - MNC"
    ::= { ncScanInterCell5 3 }

ncScanLac-e5 OBJECT-TYPE
    SYNTAX Unsigned32 (0..65535)
    ACCESS read-write
    STATUS optional
    DESCRIPTION "Inter-Freq Neighbour Cell 6 - LAC"
    ::= { ncScanInterCell5 4 }

ncScanRac-e5 OBJECT-TYPE
    SYNTAX Unsigned32 (0..65535)
    ACCESS read-write
    STATUS optional
    DESCRIPTION "Inter-Freq Neighbour Cell 6 - RAC"
    ::= { ncScanInterCell5 5 }

ncScanUarfcn-e5 OBJECT-TYPE
    SYNTAX Unsigned32 (412..10838)
    ACCESS read-write
    STATUS optional
    DESCRIPTION "Inter-Freq Neighbour Cell 6 - ARFCN"
    ::= { ncScanInterCell5 6 }

ncScanScramblingCode-e5 OBJECT-TYPE
    SYNTAX Unsigned32 (0..511)
    ACCESS read-write
    STATUS optional
    DESCRIPTION "Inter-Freq Neighbour Cell 6 - Scrambling Code"
    ::= { ncScanInterCell5 7 }

ncScanSib11-e5 OBJECT-TYPE
    SYNTAX OCTET STRING (SIZE(0..255))
    ACCESS read-write
    STATUS optional
    DESCRIPTION "Inter-Freq Neighbour Cell 6 - SIB11 decode string"
    ::= { ncScanInterCell5 8 }        


--
-- INTER-RAT NEIGHBOURS
--

-- Inter-RAT (GSM) Neighbour Cell 1

ncScanCellId-r0 OBJECT-TYPE
    SYNTAX INTEGER (0..268435455)
    ACCESS read-write
    STATUS optional
    DESCRIPTION "Inter-RAT (GSM) Neighbour Cell 1 - Cell ID (0 - 268435455)"
    ::= { ncScanInterRatCell0 1 }

ncScanArfcn-r0 OBJECT-TYPE
    SYNTAX Unsigned32 (0..1023)
    ACCESS read-write
    STATUS optional
    DESCRIPTION "Inter-RAT (GSM) Neighbour Cell 1 - ARFCN"
    ::= { ncScanInterRatCell0 2 }

ncScanBcc-r0 OBJECT-TYPE
    SYNTAX Unsigned32 (0..7)
    ACCESS read-write
    STATUS optional
    DESCRIPTION "Inter-RAT (GSM) Neighbour Cell 1 - BCC"
    ::= { ncScanInterRatCell0 3 }

ncScanNcc-r0 OBJECT-TYPE
    SYNTAX Unsigned32 (0..7)
    ACCESS read-write
    STATUS optional
    DESCRIPTION "Inter-RAT (GSM) Neighbour Cell 1 - NCC"
    ::= { ncScanInterRatCell0 4 }

ncScanMnc-r0 OBJECT-TYPE
    SYNTAX Unsigned32 (0..999)
    ACCESS read-write
    STATUS optional
    DESCRIPTION "Inter-RAT (GSM) Neighbour Cell 1 - MNC"
    ::= { ncScanInterRatCell0 5 }

ncScanMcc-r0 OBJECT-TYPE
    SYNTAX Unsigned32 (0..999)
    ACCESS read-write
    STATUS optional
    DESCRIPTION "Inter-RAT (GSM) Neighbour Cell 1 - MCC"
    ::= { ncScanInterRatCell0 6 }
    
ncScanLac-r0 OBJECT-TYPE
    SYNTAX Unsigned32 (0..65535)
    ACCESS read-write
    STATUS optional
    DESCRIPTION "Inter-RAT (GSM) Neighbour Cell 1 - LAC"
    ::= { ncScanInterRatCell0 7 }

ncScanIsPcs-r0 OBJECT-TYPE
    SYNTAX Unsigned32 (0..1)
    ACCESS read-write
    STATUS optional
    DESCRIPTION "Inter-RAT (GSM) Neighbour Cell 1 - PCS(1)/DCS(0)"
    ::= { ncScanInterRatCell0 8 }
    
ncScanSI2-r0 OBJECT-TYPE
    SYNTAX OCTET STRING (SIZE(0..255))
    ACCESS read-write
    STATUS optional
    DESCRIPTION "Inter-RAT (GSM) Neighbour Cell 1 - SI2 decode string"
    ::= { ncScanInterRatCell0 9 }    

-- Inter-RAT (GSM) Neighbour Cell 2

ncScanCellId-r1 OBJECT-TYPE
    SYNTAX INTEGER (0..268435455)
    ACCESS read-write
    STATUS optional
    DESCRIPTION "Inter-RAT (GSM) Neighbour Cell 2 - Cell ID (0 - 268435455)"
    ::= { ncScanInterRatCell1 1 }

ncScanArfcn-r1 OBJECT-TYPE
    SYNTAX Unsigned32 (0..1023)
    ACCESS read-write
    STATUS optional
    DESCRIPTION "Inter-RAT (GSM) Neighbour Cell 2 - ARFCN"
    ::= { ncScanInterRatCell1 2 }

ncScanBcc-r1 OBJECT-TYPE
    SYNTAX Unsigned32 (0..7)
    ACCESS read-write
    STATUS optional
    DESCRIPTION "Inter-RAT (GSM) Neighbour Cell 2 - BCC"
    ::= { ncScanInterRatCell1 3 }

ncScanNcc-r1 OBJECT-TYPE
    SYNTAX Unsigned32 (0..7)
    ACCESS read-write
    STATUS optional
    DESCRIPTION "Inter-RAT (GSM) Neighbour Cell 2 - NCC"
    ::= { ncScanInterRatCell1 4 }

ncScanMnc-r1 OBJECT-TYPE
    SYNTAX Unsigned32 (0..999)
    ACCESS read-write
    STATUS optional
    DESCRIPTION "Inter-RAT (GSM) Neighbour Cell 2 - MNC"
    ::= { ncScanInterRatCell1 5 }

ncScanMcc-r1 OBJECT-TYPE
    SYNTAX Unsigned32 (0..999)
    ACCESS read-write
    STATUS optional
    DESCRIPTION "Inter-RAT (GSM) Neighbour Cell 2 - MCC"
    ::= { ncScanInterRatCell1 6 }
    
ncScanLac-r1 OBJECT-TYPE
    SYNTAX Unsigned32 (0..65535)
    ACCESS read-write
    STATUS optional
    DESCRIPTION "Inter-RAT (GSM) Neighbour Cell 2 - LAC"
    ::= { ncScanInterRatCell1 7 }

ncScanIsPcs-r1 OBJECT-TYPE
    SYNTAX Unsigned32 (0..1)
    ACCESS read-write
    STATUS optional
    DESCRIPTION "Inter-RAT (GSM) Neighbour Cell 2 - PCS(1)/DCS(0)"
    ::= { ncScanInterRatCell1 8 }
    
ncScanSI2-r1 OBJECT-TYPE
    SYNTAX OCTET STRING (SIZE(0..255))
    ACCESS read-write
    STATUS optional
    DESCRIPTION "Inter-RAT (GSM) Neighbour Cell 2 - SI2 decode string"
    ::= { ncScanInterRatCell1 9 }       

-- Inter-RAT (GSM) Neighbour Cell 3

ncScanCellId-r2 OBJECT-TYPE
    SYNTAX INTEGER (0..268435455)
    ACCESS read-write
    STATUS optional
    DESCRIPTION "Inter-RAT (GSM) Neighbour Cell 3 - Cell ID (0 - 268435455)"
    ::= { ncScanInterRatCell2 1 }

ncScanArfcn-r2 OBJECT-TYPE
    SYNTAX Unsigned32 (0..1023)
    ACCESS read-write
    STATUS optional
    DESCRIPTION "Inter-RAT (GSM) Neighbour Cell 3 - ARFCN"
    ::= { ncScanInterRatCell2 2 }

ncScanBcc-r2 OBJECT-TYPE
    SYNTAX Unsigned32 (0..7)
    ACCESS read-write
    STATUS optional
    DESCRIPTION "Inter-RAT (GSM) Neighbour Cell 3 - BCC"
    ::= { ncScanInterRatCell2 3 }

ncScanNcc-r2 OBJECT-TYPE
    SYNTAX Unsigned32 (0..7)
    ACCESS read-write
    STATUS optional
    DESCRIPTION "Inter-RAT (GSM) Neighbour Cell 3 - NCC"
    ::= { ncScanInterRatCell2 4 }

ncScanMnc-r2 OBJECT-TYPE
    SYNTAX Unsigned32 (0..999)
    ACCESS read-write
    STATUS optional
    DESCRIPTION "Inter-RAT (GSM) Neighbour Cell 3 - MNC"
    ::= { ncScanInterRatCell2 5 }

ncScanMcc-r2 OBJECT-TYPE
    SYNTAX Unsigned32 (0..999)
    ACCESS read-write
    STATUS optional
    DESCRIPTION "Inter-RAT (GSM) Neighbour Cell 3 - MCC"
    ::= { ncScanInterRatCell2 6 }
    
ncScanLac-r2 OBJECT-TYPE
    SYNTAX Unsigned32 (0..65535)
    ACCESS read-write
    STATUS optional
    DESCRIPTION "Inter-RAT (GSM) Neighbour Cell 3 - LAC"
    ::= { ncScanInterRatCell2 7 }

ncScanIsPcs-r2 OBJECT-TYPE
    SYNTAX Unsigned32 (0..1)
    ACCESS read-write
    STATUS optional
    DESCRIPTION "Inter-RAT (GSM) Neighbour Cell 3 - PCS(1)/DCS(0)"
    ::= { ncScanInterRatCell2 8 }
    
ncScanSI2-r2 OBJECT-TYPE
    SYNTAX OCTET STRING (SIZE(0..255))
    ACCESS read-write
    STATUS optional
    DESCRIPTION "Inter-RAT (GSM) Neighbour Cell 3 - SI2 decode string"
    ::= { ncScanInterRatCell2 9 }           

-- Inter-RAT (GSM) Neighbour Cell 4

ncScanCellId-r3 OBJECT-TYPE
    SYNTAX INTEGER (0..268435455)
    ACCESS read-write
    STATUS optional
    DESCRIPTION "Inter-RAT (GSM) Neighbour Cell 4 - Cell ID (0 - 268435455)"
    ::= { ncScanInterRatCell3 1 }

ncScanArfcn-r3 OBJECT-TYPE
    SYNTAX Unsigned32 (0..1023)
    ACCESS read-write
    STATUS optional
    DESCRIPTION "Inter-RAT (GSM) Neighbour Cell 4 - ARFCN"
    ::= { ncScanInterRatCell3 2 }

ncScanBcc-r3 OBJECT-TYPE
    SYNTAX Unsigned32 (0..7)
    ACCESS read-write
    STATUS optional
    DESCRIPTION "Inter-RAT (GSM) Neighbour Cell 4 - BCC"
    ::= { ncScanInterRatCell3 3 }

ncScanNcc-r3 OBJECT-TYPE
    SYNTAX Unsigned32 (0..7)
    ACCESS read-write
    STATUS optional
    DESCRIPTION "Inter-RAT (GSM) Neighbour Cell 4 - NCC"
    ::= { ncScanInterRatCell3 4 }

ncScanMnc-r3 OBJECT-TYPE
    SYNTAX Unsigned32 (0..999)
    ACCESS read-write
    STATUS optional
    DESCRIPTION "Inter-RAT (GSM) Neighbour Cell 4 - MNC"
    ::= { ncScanInterRatCell3 5 }

ncScanMcc-r3 OBJECT-TYPE
    SYNTAX Unsigned32 (0..999)
    ACCESS read-write
    STATUS optional
    DESCRIPTION "Inter-RAT (GSM) Neighbour Cell 4 - MCC"
    ::= { ncScanInterRatCell3 6 }

ncScanLac-r3 OBJECT-TYPE
    SYNTAX Unsigned32 (0..65535)
    ACCESS read-write
    STATUS optional
    DESCRIPTION "Inter-RAT (GSM) Neighbour Cell 4 - LAC"
    ::= { ncScanInterRatCell3 7 }
    
ncScanIsPcs-r3 OBJECT-TYPE
    SYNTAX Unsigned32 (0..1)
    ACCESS read-write
    STATUS optional
    DESCRIPTION "Inter-RAT (GSM) Neighbour Cell 4 - PCS(1)/DCS(0)"
    ::= { ncScanInterRatCell3 8 }
    
ncScanSI2-r3 OBJECT-TYPE
    SYNTAX OCTET STRING (SIZE(0..255))
    ACCESS read-write
    STATUS optional
    DESCRIPTION "Inter-RAT (GSM) Neighbour Cell 4 - SI2 decode string"
    ::= { ncScanInterRatCell3 9 }        

-- Inter-RAT (GSM) Neighbour Cell 5

ncScanCellId-r4 OBJECT-TYPE
    SYNTAX INTEGER (0..268435455)
    ACCESS read-write
    STATUS optional
    DESCRIPTION "Inter-RAT (GSM) Neighbour Cell 5 - Cell ID (0 - 268435455)"
    ::= { ncScanInterRatCell4 1 }

ncScanArfcn-r4 OBJECT-TYPE
    SYNTAX Unsigned32 (0..1023)
    ACCESS read-write
    STATUS optional
    DESCRIPTION "Inter-RAT (GSM) Neighbour Cell 5 - ARFCN"
    ::= { ncScanInterRatCell4 2 }

ncScanBcc-r4 OBJECT-TYPE
    SYNTAX Unsigned32 (0..7)
    ACCESS read-write
    STATUS optional
    DESCRIPTION "Inter-RAT (GSM) Neighbour Cell 5 - BCC"
    ::= { ncScanInterRatCell4 3 }

ncScanNcc-r4 OBJECT-TYPE
    SYNTAX Unsigned32 (0..7)
    ACCESS read-write
    STATUS optional
    DESCRIPTION "Inter-RAT (GSM) Neighbour Cell 5 - NCC"
    ::= { ncScanInterRatCell4 4 }

ncScanMnc-r4 OBJECT-TYPE
    SYNTAX Unsigned32 (0..999)
    ACCESS read-write
    STATUS optional
    DESCRIPTION "Inter-RAT (GSM) Neighbour Cell 5 - MNC"
    ::= { ncScanInterRatCell4 5 }

ncScanMcc-r4 OBJECT-TYPE
    SYNTAX Unsigned32 (0..999)
    ACCESS read-write
    STATUS optional
    DESCRIPTION "Inter-RAT (GSM) Neighbour Cell 5 - MCC"
    ::= { ncScanInterRatCell4 6 }

ncScanLac-r4 OBJECT-TYPE
    SYNTAX Unsigned32 (0..65535)
    ACCESS read-write
    STATUS optional
    DESCRIPTION "Inter-RAT (GSM) Neighbour Cell 5 - LAC"
    ::= { ncScanInterRatCell4 7 }
    
ncScanIsPcs-r4 OBJECT-TYPE
    SYNTAX Unsigned32 (0..1)
    ACCESS read-write
    STATUS optional
    DESCRIPTION "Inter-RAT (GSM) Neighbour Cell 5 - PCS(1)/DCS(0)"
    ::= { ncScanInterRatCell4 8 }
    
ncScanSI2-r4 OBJECT-TYPE
    SYNTAX OCTET STRING (SIZE(0..255))
    ACCESS read-write
    STATUS optional
    DESCRIPTION "Inter-RAT (GSM) Neighbour Cell 5 - SI2 decode string"
    ::= { ncScanInterRatCell4 9 }        

-- Inter-RAT (GSM) Neighbour Cell 6

ncScanCellId-r5 OBJECT-TYPE
    SYNTAX INTEGER (0..268435455)
    ACCESS read-write
    STATUS optional
    DESCRIPTION "Inter-RAT (GSM) Neighbour Cell 6 - Cell ID (0 - 268435455)"
    ::= { ncScanInterRatCell5 1 }

ncScanArfcn-r5 OBJECT-TYPE
    SYNTAX Unsigned32 (0..1023)
    ACCESS read-write
    STATUS optional
    DESCRIPTION "Inter-RAT (GSM) Neighbour Cell 6 - ARFCN"
    ::= { ncScanInterRatCell5 2 }

ncScanBcc-r5 OBJECT-TYPE
    SYNTAX Unsigned32 (0..7)
    ACCESS read-write
    STATUS optional
    DESCRIPTION "Inter-RAT (GSM) Neighbour Cell 6 - BCC"
    ::= { ncScanInterRatCell5 3 }

ncScanNcc-r5 OBJECT-TYPE
    SYNTAX Unsigned32 (0..7)
    ACCESS read-write
    STATUS optional
    DESCRIPTION "Inter-RAT (GSM) Neighbour Cell 6 - NCC"
    ::= { ncScanInterRatCell5 4 }

ncScanMnc-r5 OBJECT-TYPE
    SYNTAX Unsigned32 (0..999)
    ACCESS read-write
    STATUS optional
    DESCRIPTION "Inter-RAT (GSM) Neighbour Cell 6 - MNC"
    ::= { ncScanInterRatCell5 5 }

ncScanMcc-r5 OBJECT-TYPE
    SYNTAX Unsigned32 (0..999)
    ACCESS read-write
    STATUS optional
    DESCRIPTION "Inter-RAT (GSM) Neighbour Cell 6 - MCC"
    ::= { ncScanInterRatCell5 6 }

ncScanLac-r5 OBJECT-TYPE
    SYNTAX Unsigned32 (0..65535)
    ACCESS read-write
    STATUS optional
    DESCRIPTION "Inter-RAT (GSM) Neighbour Cell 6 - LAC"
    ::= { ncScanInterRatCell5 7 }
    
ncScanIsPcs-r5 OBJECT-TYPE
    SYNTAX Unsigned32 (0..1)
    ACCESS read-write
    STATUS optional
    DESCRIPTION "Inter-RAT (GSM) Neighbour Cell 6 - PCS(1)/DCS(0)"
    ::= { ncScanInterRatCell5 8 }
    
ncScanSI2-r5 OBJECT-TYPE
    SYNTAX OCTET STRING (SIZE(0..255))
    ACCESS read-write
    STATUS optional
    DESCRIPTION "Inter-RAT (GSM) Neighbour Cell 6 - SI2 decode string"
    ::= { ncScanInterRatCell5 9 }             
    
--IP stuff

iuCoreNetIpAddress OBJECT-TYPE
    SYNTAX IpAddress
    ACCESS read-write
    STATUS optional
    DESCRIPTION "IP address of core network (or femto gateway)
                 for Iu interface."
    ::= { iuAddressing 1 }

iuSctpLocalPort OBJECT-TYPE
    SYNTAX Unsigned32 (1024..65535)
    ACCESS read-write
    STATUS optional
    DESCRIPTION "Local (FAP) port number for SCTP on Iu."
    ::= { iuAddressing 2 }

iuSctpRemotePort OBJECT-TYPE
    SYNTAX Unsigned32 (1024..65535)
    ACCESS read-write
    STATUS optional
    DESCRIPTION "Remote (CN/FGW) port number for SCTP on Iu."
    ::= { iuAddressing 3 }

iuFemtoPointCode OBJECT-TYPE
    SYNTAX Unsigned32 (0..16363)
    ACCESS read-write
    STATUS optional
    DESCRIPTION "Local (FAP) point code for both CS and PS on Iu."
    ::= { iuAddressing 4 }

iuCoreNetCsPointCode OBJECT-TYPE
    SYNTAX Unsigned32 (0..16363)
    ACCESS read-write
    STATUS optional
    DESCRIPTION "Remote (CN/FGW) point code for CS on Iu."
    ::= { iuAddressing 5 }

iuCoreNetPsPointCode OBJECT-TYPE
    SYNTAX Unsigned32 (0..16363)
    ACCESS read-write
    STATUS optional
    DESCRIPTION "Remote (CN/FGW) point code for PS on Iu."
    ::= { iuAddressing 6 }

iuStaticCoreNetIpAddress OBJECT-TYPE
    SYNTAX Unsigned32 (0..1)
    ACCESS read-write
    STATUS optional
    DESCRIPTION "0 = Use FGW-assigned CN IpAddress, 1 = Use static CN IpAddress."
    ::= { iuAddressing 7 }


m3uaAspId OBJECT-TYPE
    SYNTAX Unsigned32 (1..3600)
    ACCESS read-write
    STATUS optional
    DESCRIPTION "M3UA Asp Id."
    ::= { m3ua 1 }

m3uaDoubleExchange OBJECT-TYPE
    SYNTAX Unsigned32 (0..1)
    ACCESS read-write
    STATUS optional
    DESCRIPTION "M3UA Double Exchange"
    ::= { m3ua 2 }

m3uaTrafficMode OBJECT-TYPE
    SYNTAX Unsigned32 (0..4)
    ACCESS read-write
    STATUS optional
    DESCRIPTION "M3UA Traffic Mode"
    ::= { m3ua 3 }

m3uaLocalRoutingContext OBJECT-TYPE
    SYNTAX Unsigned32 (0..4294967295)
    ACCESS read-write
    STATUS optional
    DESCRIPTION "M3UA Local Routing Context"
    ::= { m3ua 4 }

m3uaRemoteCsRoutingContext OBJECT-TYPE
    SYNTAX Unsigned32 (0..9999)
    ACCESS read-write
    STATUS optional
    DESCRIPTION "M3UA Remote Cs Routing Context"
    ::= { m3ua 5 }

m3uaRemotePsRoutingContext OBJECT-TYPE
    SYNTAX Unsigned32 (0..9999)
    ACCESS read-write
    STATUS optional
    DESCRIPTION "M3UA Remote Ps Routing Context"
    ::= { m3ua 6 }

m3uaAspUpAckWaitTimer OBJECT-TYPE
    SYNTAX Unsigned32 (1..9999)
    ACCESS read-write
    STATUS optional
    DESCRIPTION "Interval in seconds to wait for ASP UP ACK"
    ::= { m3ua 7 }

m3uaAspUpAckMaxRetries OBJECT-TYPE
    SYNTAX Unsigned32 (0..9999)
    ACCESS read-write
    STATUS optional
    DESCRIPTION "Number of times to retry ASP UP procedure"
    ::= { m3ua 8 }

sccpConnEstTimer OBJECT-TYPE
    SYNTAX Unsigned32 (1..3600)
    ACCESS read-write
    STATUS optional
    DESCRIPTION "Interval in seconds to wait for Sccp Connection
                 Confirm on from Core Network on Iu."
    ::= { sccp 1 }

sccpInactivityReceiveTimer OBJECT-TYPE
    SYNTAX Unsigned32 (0..3600)
    ACCESS read-write
    STATUS optional
    DESCRIPTION "Tiar.  Interval in seconds allowed between receiving
                 Sccp Inactivity Test messages from Core Network.
                 Set to 0 to disable checking of received IT messages."
    ::= { sccp 2 }

sccpInactivitySendTimer OBJECT-TYPE
    SYNTAX Unsigned32 (0..3600)
    ACCESS read-write
    STATUS optional
    DESCRIPTION "Tias.  Interval in seconds allowed between sending Sccp
                 Inactivity Test messages to Core Network.
                 Set to 0 to disable sending IT messages."
    ::= { sccp 3 }

sccpReleaseTimer OBJECT-TYPE
    SYNTAX Unsigned32 (1..3600)
    ACCESS read-write
    STATUS optional
    DESCRIPTION "Interval in seconds to wait for Sccp Release
                 Complete from Core Network on Iu."
    ::= { sccp 4 }

sccpReleaseIntervalTimer OBJECT-TYPE
    SYNTAX Unsigned32 (1..3600)
    ACCESS read-write
    STATUS optional
    DESCRIPTION "Interval in seconds to wait before failing Sccp
                 Release procedure with Core Network on Iu."
    ::= { sccp 5 }

sccpDpcInCalledParty OBJECT-TYPE
    SYNTAX Unsigned32 (0..1)
    ACCESS read-write
    STATUS optional
    DESCRIPTION "Include the Destination Point Code in the Called
                 Party Address sending TO Core Network."
    ::= { sccp 6 }

sctpMaxInitRetransmits OBJECT-TYPE
    SYNTAX Unsigned32 (0..9999)
    ACCESS read-write
    STATUS optional
    DESCRIPTION "Number of times to retransmit the SCTP INIT message."
    ::= { sctp 1 }

sctpT1InitTimer OBJECT-TYPE
    SYNTAX Unsigned32 (0..9999)
    ACCESS read-write
    STATUS optional
    DESCRIPTION "Number of seconds between SCTP INIT retransmissions"
    ::= { sctp 2 }

sctpMaxCookieEchoRetransmits OBJECT-TYPE
    SYNTAX Unsigned32 (0..9999)
    ACCESS read-write
    STATUS optional
    DESCRIPTION "Number of times to retransmit the SCTP COOKIE ECHO message."
    ::= { sctp 3 }

sctpT1CookieTimer OBJECT-TYPE
    SYNTAX Unsigned32 (0..9999)
    ACCESS read-write
    STATUS optional
    DESCRIPTION "Number of seconds between SCTP COOKIE retransmissions."
    ::= { sctp 4 }

sctpT2ShutdownTimer OBJECT-TYPE
    SYNTAX Unsigned32 (0..9999)
    ACCESS read-write
    STATUS optional
    DESCRIPTION "Number of seconds between SCTP SHUTDOWN retransmissions."
    ::= { sctp 5 }

sctpRtoInitial OBJECT-TYPE
    SYNTAX Unsigned32 (100..3000)
    ACCESS read-write
    STATUS optional
    DESCRIPTION "Initial time in milliseconds between SCTP retransmissions."
    ::= { sctp 6 }

sctpRtoMin OBJECT-TYPE
    SYNTAX Unsigned32 (100..1000)
    ACCESS read-write
    STATUS optional
    DESCRIPTION "Minimum time in milliseconds between SCTP retransmissions."
    ::= { sctp 7 }

sctpRtoMax OBJECT-TYPE
    SYNTAX Unsigned32 (100..10000)
    ACCESS read-write
    STATUS optional
    DESCRIPTION "Maximum time in milliseconds between SCTP retransmissions."
    ::= { sctp 8 }

sctpDelayedSackTimer OBJECT-TYPE
    SYNTAX Unsigned32 (0..9999)
    ACCESS read-write
    STATUS optional
    DESCRIPTION "Number of milliseconds delay before sending SCTP SACK."
    ::= { sctp 9 }

sctpRestartDelayTimer OBJECT-TYPE
    SYNTAX Unsigned32 (0..9999)
    ACCESS read-write
    STATUS optional
    DESCRIPTION "Number of seconds to wait after failure before attempting Iu restart."
    ::= { sctp 10 }

sctpHeartbeatTimer OBJECT-TYPE
    SYNTAX Unsigned32 (0..9999)
    ACCESS read-write
    STATUS optional
    DESCRIPTION "Number of seconds between sending SCTP HEARTBEAT messages."
    ::= { sctp 11 }

sctpOutboundStreams OBJECT-TYPE
    SYNTAX Unsigned32 (0..9999)
    ACCESS read-write
    STATUS optional
    DESCRIPTION "Number of outbound SCTP streams."
    ::= { sctp 12 }

sctpInboundStreams OBJECT-TYPE
    SYNTAX Unsigned32 (0..9999)
    ACCESS read-write
    STATUS optional
    DESCRIPTION "Number of inbound SCTP streams."
    ::= { sctp 13 }

sctpAssocMaxRetransmits OBJECT-TYPE
    SYNTAX Unsigned32 (0..9999)
    ACCESS read-write
    STATUS optional
    DESCRIPTION "Number of times to retransmit the SCTP ASSOC message."
    ::= { sctp 14 }

sctpSendAbortOnFailure OBJECT-TYPE
    SYNTAX Unsigned32 (0..9999)
    ACCESS read-write
    STATUS optional
    DESCRIPTION "Send the SCTP ABORT message when system failure detected?"
    ::= { sctp 15 }

sctpEnableTrace OBJECT-TYPE
    SYNTAX Unsigned32 (0..9999)
    ACCESS read-write
    STATUS optional
    DESCRIPTION "Enable low level Socket tracing?"
    ::= { sctp 16 }

sctpShutdownRetransmits OBJECT-TYPE
    SYNTAX Unsigned32 (0..9999)
    ACCESS read-write
    STATUS optional
    DESCRIPTION "Number of times to retransmit the SCTP SHUTDOWN message."
    ::= { sctp 17 }

ranapTRatRTimer OBJECT-TYPE
    SYNTAX Unsigned32 (1..3600)
    ACCESS read-write
    STATUS optional
    DESCRIPTION "Interval in seconds to retry sending RANAP RESET on Iu."
    ::= { ranap 1 }

ranapTRatCTimer OBJECT-TYPE
    SYNTAX Unsigned32 (1..3600)
    ACCESS read-write
    STATUS optional
    DESCRIPTION "Interval in seconds to wait before sending RANAP RESET ACK on Iu."
    ::= { ranap 2 }

ranapTIURelReqTimer OBJECT-TYPE
    SYNTAX Unsigned32 (1..10)
    ACCESS read-write
    STATUS optional
    DESCRIPTION "Interval in seconds to wait Iu Release uppon transmission of Iu Release Request."
    ::= { ranap 3 }

ranapNIURelReq OBJECT-TYPE
    SYNTAX Unsigned32 (1..10)
    ACCESS read-write
    STATUS optional
    DESCRIPTION "Maximum number for Iu Release Request procedure repetition."
    ::= { ranap 4 }

ranapPsUpAddrFormat OBJECT-TYPE
    SYNTAX Unsigned32 (0..1)
    ACCESS read-write
    STATUS optional
    DESCRIPTION "1 = NSAP header bytes in User Plane Information for PS RAB Assignment, 0 = no header."
    ::= { ranap 5 }

accessControlOpen OBJECT-TYPE
    SYNTAX Unsigned32 (0..1)
    ACCESS read-write
    STATUS optional
    DESCRIPTION "1 = Access Control is Open and any UE is accepted, 0 = Access Control is Closed and only listed IMSIs are accepted."
    ::= { closedAccessControl 1 }

accessIdentificationTimer OBJECT-TYPE
    SYNTAX Unsigned32 (0..9999)
    ACCESS read-write
    STATUS optional
    DESCRIPTION "Access Identity Request Timer T3270."
    ::= { closedAccessControl 2 }

accessControlTAccCtrl OBJECT-TYPE
    SYNTAX Unsigned32 (0..1000)
    ACCESS read-write
    STATUS optional
    DESCRIPTION "Time in seconds to delay before a call is released where for a UE in call the IMSI, which was previously permitted, is removed from the list of permitted IMSIs."
    ::= { closedAccessControl 3 }

accessControlImsi1 OBJECT-TYPE
    SYNTAX OCTET STRING (SIZE(21))
    ACCESS read-write
    STATUS optional
    DESCRIPTION "The IMSI of a UE that is permitted to use this femto cell in Closed Access Control mode."
    ::= { closedAccessControl 4 }

accessControlImsi2 OBJECT-TYPE
    SYNTAX OCTET STRING (SIZE(21))
    ACCESS read-write
    STATUS optional
    DESCRIPTION "The IMSI of a UE that is permitted to use this femto cell in Closed Access Control mode."
    ::= { closedAccessControl 5 }

accessControlImsi3 OBJECT-TYPE
    SYNTAX OCTET STRING (SIZE(21))
    ACCESS read-write
    STATUS optional
    DESCRIPTION "The IMSI of a UE that is permitted to use this femto cell in Closed Access Control mode."
    ::= { closedAccessControl 6 }

accessControlImsi4 OBJECT-TYPE
    SYNTAX OCTET STRING (SIZE(21))
    ACCESS read-write
    STATUS optional
    DESCRIPTION "The IMSI of a UE that is permitted to use this femto cell in Closed Access Control mode."
    ::= { closedAccessControl 7 }

accessControlImsi5 OBJECT-TYPE
    SYNTAX OCTET STRING (SIZE(21))
    ACCESS read-write
    STATUS optional
    DESCRIPTION "The IMSI of a UE that is permitted to use this femto cell in Closed Access Control mode."
    ::= { closedAccessControl 8 }

accessControlImsi6 OBJECT-TYPE
    SYNTAX OCTET STRING (SIZE(21))
    ACCESS read-write
    STATUS optional
    DESCRIPTION "The IMSI of a UE that is permitted to use this femto cell in Closed Access Control mode."
    ::= { closedAccessControl 9 }

accessControlImsi7 OBJECT-TYPE
    SYNTAX OCTET STRING (SIZE(21))
    ACCESS read-write
    STATUS optional
    DESCRIPTION "The IMSI of a UE that is permitted to use this femto cell in Closed Access Control mode."
    ::= { closedAccessControl 10 }

accessControlImsi8 OBJECT-TYPE
    SYNTAX OCTET STRING (SIZE(21))
    ACCESS read-write
    STATUS optional
    DESCRIPTION "The IMSI of a UE that is permitted to use this femto cell in Closed Access Control mode."
    ::= { closedAccessControl 11 }

accessControlImsi9 OBJECT-TYPE
    SYNTAX OCTET STRING (SIZE(21))
    ACCESS read-write
    STATUS optional
    DESCRIPTION "The IMSI of a UE that is permitted to use this femto cell in Closed Access Control mode."
    ::= { closedAccessControl 12 }

accessControlImsi10 OBJECT-TYPE
    SYNTAX OCTET STRING (SIZE(21))
    ACCESS read-write
    STATUS optional
    DESCRIPTION "The IMSI of a UE that is permitted to use this femto cell in Closed Access Control mode."
    ::= { closedAccessControl 13 }

accessControlImsi11 OBJECT-TYPE
    SYNTAX OCTET STRING (SIZE(21))
    ACCESS read-write
    STATUS optional
    DESCRIPTION "The IMSI of a UE that is permitted to use this femto cell in Closed Access Control mode."
    ::= { closedAccessControl 14 }

accessControlImsi12 OBJECT-TYPE
    SYNTAX OCTET STRING (SIZE(21))
    ACCESS read-write
    STATUS optional
    DESCRIPTION "The IMSI of a UE that is permitted to use this femto cell in Closed Access Control mode."
    ::= { closedAccessControl 15 }

accessControlImsi13 OBJECT-TYPE
    SYNTAX OCTET STRING (SIZE(21))
    ACCESS read-write
    STATUS optional
    DESCRIPTION "The IMSI of a UE that is permitted to use this femto cell in Closed Access Control mode."
    ::= { closedAccessControl 16 }

accessControlImsi14 OBJECT-TYPE
    SYNTAX OCTET STRING (SIZE(21))
    ACCESS read-write
    STATUS optional
    DESCRIPTION "The IMSI of a UE that is permitted to use this femto cell in Closed Access Control mode."
    ::= { closedAccessControl 17 }

accessControlImsi15 OBJECT-TYPE
    SYNTAX OCTET STRING (SIZE(21))
    ACCESS read-write
    STATUS optional
    DESCRIPTION "The IMSI of a UE that is permitted to use this femto cell in Closed Access Control mode."
    ::= { closedAccessControl 18 }

relocationType OBJECT-TYPE
    SYNTAX Unsigned32 (0..1)
    ACCESS read-write
    STATUS optional
    DESCRIPTION "0 = UE NOT Involved, 1 = UE Involved"
    ::= { relocation 1 }

-- NOTE: relocation 2..21 previously used - please do not re-use these numbers! - Dm 05jan09 --

measurementPeriod OBJECT-TYPE
    SYNTAX Unsigned32 (0..15)
    ACCESS read-write
    STATUS optional
    DESCRIPTION "Measurement Reporting Periodicity:
                 0 = Measurement Reporting Off
                 1 = 250mS, 2 = 500mS, 3 = 1000mS,
                 4 = 2000mS, 5 = 3000mS, 6 = 4000mS,
                 7 = 6000mS, 8 = 8000mS, 9 = 12000mS,
                 10 = 16000mS, 11 = 20000mS, 12 = 24000mS,
                 13 = 28000mS, 14 = 32000mS, 15 = 64000ms"
    ::= { relocation 22 }

tRelocPrepare OBJECT-TYPE
    SYNTAX Unsigned32 (0..65535)
    ACCESS read-write
    STATUS optional
    DESCRIPTION "3GPP 25.413 Sub Section 8.6.3"
    ::= { relocation 25 }

tRelocOverall OBJECT-TYPE
    SYNTAX Unsigned32 (0..65535)
    ACCESS read-write
    STATUS optional
    DESCRIPTION "3GPP 25.413 Sub Section 8.5.3"
    ::= { relocation 26 }

-- Please do not re-use the following (param is obsolete - use enableHandoverToMacro instead).
-- relocationOn OBJECT-TYPE
--     SYNTAX Unsigned32 (0..1)
--    ACCESS read-write
--    STATUS optional
--    DESCRIPTION "Non 0 = Enable Measurement Based Relocation
--                 0 = No Relocation (unless blind handover timer enabled)"
--    ::= { relocation 27 }

relocationBackoff OBJECT-TYPE
    SYNTAX Unsigned32 (1..300)
    ACCESS read-write
    STATUS optional
    DESCRIPTION "Number of seconds to wait after a failed Relocation before
               making another attempt"
    ::= { relocation 28 }

-- Please do not re-use the following (param is obsolete).
--relocationOffset OBJECT-TYPE
--    SYNTAX INTEGER (-115..115)
--    ACCESS read-write
--    STATUS optional
--    DESCRIPTION "Value added to the averaged RSCP of a neighbour cell to make
--               it more or less attractive as a Relocation candidate."
--    ::= { relocation 29 }

-- Please do not re-use the following (param is obsolete).
--compressedModePeriod OBJECT-TYPE
--    SYNTAX Unsigned32 (1..60)
--    ACCESS read-write
--    STATUS optional
--    DESCRIPTION "Number of seconds to measure inter frequency neighbour cells"
--    ::= { relocation 30 }

measurementLoggerIp OBJECT-TYPE
    SYNTAX Unsigned32 (1..60)
    ACCESS read-write
    STATUS optional
    DESCRIPTION "IP address of destination machine running measurement report logger"
    ::= { relocation 31 }

measurementLoggerPort OBJECT-TYPE
    SYNTAX Unsigned32 (0..65535)
    ACCESS read-write
    STATUS optional
    DESCRIPTION "UDP Port to send measurement reports to on destination machine"
    ::= { relocation 32 }

-- Please do not re-use the following (param is obsolete).
-- compressedMode-triggerOnEvent OBJECT-TYPE
--     SYNTAX Unsigned32 (0..4)
--     ACCESS read-write
--     STATUS optional
--     DESCRIPTION "Trigger compressed mode on : 0=event2d, 1=event1f"
--     ::= { relocation 33 }

tRncBaselineReleaseInfo OBJECT-TYPE
     SYNTAX Unsigned32 (0..4)
     ACCESS read-write
     STATUS optional
     DESCRIPTION "RNC Baseline release info - RNC capable of 0= R99 only, 1= +Rel4, 2= +Rel5, 3= +Rel6"
     ::= { relocation 34 }

enableIntraRelocation OBJECT-TYPE
     SYNTAX Unsigned32 (0..1)
     ACCESS read-write
     STATUS optional
     DESCRIPTION "Enable / Disable experimental Intra-Freq HO support"
     ::= { relocation 35 }

enableInterRelocation OBJECT-TYPE
     SYNTAX Unsigned32 (0..1)
     ACCESS read-write
     STATUS optional
     DESCRIPTION "Enable / Disable Inter-Freq HO support"
     ::= { relocation 36 }

enableInterRatRelocation OBJECT-TYPE
     SYNTAX Unsigned32 (0..1)
     ACCESS read-write
     STATUS optional
     DESCRIPTION "Enable / Disable Intra-RAT HO support"
     ::= { relocation 37 }
     
enableCSVoiceRelocation OBJECT-TYPE
     SYNTAX Unsigned32 (0..1)
     ACCESS read-write
     STATUS optional
     DESCRIPTION "Enable / Disable relocation on CS Voice call"
     ::= { relocation 38 }
     
enableCSVideoRelocation OBJECT-TYPE
     SYNTAX Unsigned32 (0..1)
     ACCESS read-write
     STATUS optional
     DESCRIPTION "Enable / Disable relocation on CS Video call"
     ::= { relocation 39 }
          
enablePSDataRelocation OBJECT-TYPE
     SYNTAX Unsigned32 (0..1)
     ACCESS read-write
     STATUS optional
     DESCRIPTION "Enable / Disable relocation on PS Data"
     ::= { relocation 40 }
     
e1c-Hysteresis OBJECT-TYPE
    SYNTAX Unsigned32 (0..145)
    ACCESS read-write
    STATUS optional
    DESCRIPTION "Actual value Hysteresis = IE value / 10"
    ::= { event-1c 2 }

e1c-timeToTrigger OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-1c 4 }
    
e1c-MinFemtoThreshold-ECNO OBJECT-TYPE
    SYNTAX Signed32 (-24..0)
    ACCESS read-write
    STATUS optional
    DESCRIPTION "EcNo used for Minimum Femto threshold (in dBm)"
    ::= { event-1c 6 }

e1c-MinFemtoThreshold-RSCP OBJECT-TYPE
    SYNTAX Signed32 (-115..-25)
    ACCESS read-write
    STATUS optional
    DESCRIPTION "RSCP used for Minimum Femto threshold (in dBm)"
    ::= { event-1c 7 }

e1c-MinMacroThreshold-ECNO OBJECT-TYPE
    SYNTAX Signed32 (-24..0)
    ACCESS read-write
    STATUS optional
    DESCRIPTION "EcNo used for Minimum Macro threshold (in dBm)"
    ::= { event-1c 8 }

e1c-MinMacroThreshold-RSCP OBJECT-TYPE
    SYNTAX Signed32 (-115..-25)
    ACCESS read-write
    STATUS optional
    DESCRIPTION "RSCP used for Minimum Macro threshold (in dBm)"
    ::= { event-1c 9 }
        
e1c-ReportingWindow OBJECT-TYPE
    SYNTAX Unsigned32 (0..7)
    ACCESS read-write
    STATUS optional
    DESCRIPTION "Reporting Window (reporting amount) : 0=ra1;1=ra2;2=ra4;3=ra8;4=ra16;5=ra32;6=ra64;7=ra-Infinity"
    ::= { event-1c 10 }
    
e1c-ReportingInterval OBJECT-TYPE
    SYNTAX Unsigned32 (0..7)
    ACCESS read-write
    STATUS optional
    DESCRIPTION "Periodic Reporting Interval : 0=noPeriodicalReporting;1=ri0-25;2=ri0-5;3=ri1;4=ri2;5=ri4;6=ri8;7=ri16"
	::= { event-1c 11 }

-- e1d-Hysteresis OBJECT-TYPE
--    SYNTAX Unsigned32 (0..145)
--    ACCESS read-write
--    STATUS optional
--    DESCRIPTION "Actual value Hysteresis = IE value / 10"
--    ::= { event-1d 2 }

-- e1d-timeToTrigger OBJECT-TYPE
--    SYNTAX Unsigned32 (0..15)
--    ACCESS read-write
--    STATUS optional
--    DESCRIPTION "Time to Trigger (ms) : 0=0;1=10;2=20;3=40;4=60;5=80;6=100;7=120;8=160;9=200;10=240;11=320;12=640;13=1280;14=2560;15=5000"
--    ::= { event-1d 4 }

e1-W OBJECT-TYPE
    SYNTAX Unsigned32 (0..20)
    ACCESS read-write
    STATUS optional
    DESCRIPTION "Actual value W = IE value * 0.1"
    ::= { intraFrequencyHandoverControl 5 }

e1-measurementQuantityReloc OBJECT-TYPE
    SYNTAX Unsigned32 (0..1)
    ACCESS read-write
    STATUS optional
    DESCRIPTION "Measurement Quantity (for intra relocation trigger) : 0 = EcNo; 1 = RSCP"
    ::= { intraFrequencyHandoverControl 6 }

e1-measurementQuantityServing OBJECT-TYPE
    SYNTAX Unsigned32 (0..1)
    ACCESS read-write
    STATUS optional
    DESCRIPTION "Measurement Quantity (for intra serving cell monitoring) : 0 = EcNo; 1 = RSCP"
    ::= { intraFrequencyHandoverControl 7 }

e1e-Hysteresis OBJECT-TYPE
    SYNTAX Unsigned32 (0..145)
    ACCESS read-write
    STATUS optional
    DESCRIPTION "Actual value Hysteresis = IE value / 10"
    ::= { event-1e 1 }
              
e1e-usedFreqThreshold-ECNO OBJECT-TYPE
    SYNTAX Signed32 (-24..0)
    ACCESS read-write
    STATUS optional
    DESCRIPTION "EcNo used frequency threshold (in dBm)"
    ::= { event-1e 2 }

e1e-usedFreqThreshold-RSCP OBJECT-TYPE
    SYNTAX Signed32 (-115..-25)
    ACCESS read-write
    STATUS optional
    DESCRIPTION "RSCP used frequency threshold (in dBm)"
    ::= { event-1e 3 }
    
e1e-timeToTrigger OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-1e 4 }

e1f-Hysteresis OBJECT-TYPE
    SYNTAX Unsigned32 (0..145)
    ACCESS read-write
    STATUS optional
    DESCRIPTION "Actual value Hysteresis = IE value / 10"
    ::= { event-1f 1 }
    
e1f-usedFreqThreshold-ECNO OBJECT-TYPE
    SYNTAX Signed32 (-24..0)
    ACCESS read-write
    STATUS optional
    DESCRIPTION "EcNo used frequency threshold (in dBm)"
    ::= { event-1f 2 }

e1f-usedFreqThreshold-RSCP OBJECT-TYPE
    SYNTAX Signed32 (-115..-25)
    ACCESS read-write
    STATUS optional
    DESCRIPTION "RSCP used frequency threshold (in dBm)"
    ::= { event-1f 3 }
    
e1f-timeToTrigger OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-1f 4 }

e2a-Hysteresis OBJECT-TYPE
    SYNTAX Unsigned32 (0..145)
    ACCESS read-write
    STATUS optional
    DESCRIPTION "Actual value Hysteresis = IE value / 10"
    ::= { event-2a 1 }

e2a-nonUsedFreqThreshold-ECNO OBJECT-TYPE
    SYNTAX Signed32 (-24..0)
    ACCESS read-write
    STATUS optional
    DESCRIPTION "EcNo non-used frequency threshold (in dBm)"
    ::= { event-2a 2 }

e2a-nonUsedFreqThreshold-RSCP OBJECT-TYPE
    SYNTAX Signed32 (-115..-25)
    ACCESS read-write
    STATUS optional
    DESCRIPTION "RSCP non-used frequency threshold (in dBm)"
    ::= { event-2a 3 }

e2a-timeToTrigger OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-2a 4 }

e2b-Hysteresis OBJECT-TYPE
    SYNTAX Unsigned32 (0..145)
    ACCESS read-write
    STATUS optional
    DESCRIPTION "Actual value Hysteresis = IE value / 10"
    ::= { event-2b 1 }

e2b-nonUsedFreqThreshold-ECNO OBJECT-TYPE
    SYNTAX Signed32 (-24..0)
    ACCESS read-write
    STATUS optional
    DESCRIPTION "EcNo non-used frequency threshold (in dBm)"
    ::= { event-2b 2 }

e2b-nonUsedFreqThreshold-RSCP OBJECT-TYPE
    SYNTAX Signed32 (-115..-25)
    ACCESS read-write
    STATUS optional
    DESCRIPTION "RSCP non-used frequency threshold (in dBm)"
    ::= { event-2b 3 }

e2b-timeToTrigger OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-2b 4 }
    
e2b-usedFreqThreshold-ECNO OBJECT-TYPE
    SYNTAX Signed32 (-24..0)
    ACCESS read-write
    STATUS optional
    DESCRIPTION "EcNo used frequency threshold (in dBm)"
    ::= { event-2b 5 }

e2b-usedFreqThreshold-RSCP OBJECT-TYPE
    SYNTAX Signed32 (-115..-25)
    ACCESS read-write
    STATUS optional
    DESCRIPTION "RSCP used frequency threshold (in dBm)"
    ::= { event-2b 6 }

e2c-Hysteresis OBJECT-TYPE
    SYNTAX Unsigned32 (0..145)
    ACCESS read-write
    STATUS optional
    DESCRIPTION "Actual value Hysteresis = IE value / 10"
    ::= { event-2c 1 }

e2c-nonUsedFreqThreshold-ECNO OBJECT-TYPE
    SYNTAX Signed32 (-24..0)
    ACCESS read-write
    STATUS optional
    DESCRIPTION "EcNo non-used frequency threshold (in dBm)"
    ::= { event-2c 2 }

e2c-nonUsedFreqThreshold-RSCP OBJECT-TYPE
    SYNTAX Signed32 (-115..-25)
    ACCESS read-write
    STATUS optional
    DESCRIPTION "RSCP non-used frequency threshold (in dBm)"
    ::= { event-2c 3 }

e2c-timeToTrigger OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-2c 4 }

e2d-Hysteresis-e OBJECT-TYPE
    SYNTAX Unsigned32 (0..145)
    ACCESS read-write
    STATUS optional
    DESCRIPTION "Actual value Hysteresis = IE value / 10"
    ::= { event-2d-inter 1 }

e2d-usedFreqThreshold-ECNO-e OBJECT-TYPE
    SYNTAX Signed32 (-24..0)
    ACCESS read-write
    STATUS optional
    DESCRIPTION "EcNo used frequency threshold (in dBm)"
    ::= { event-2d-inter 2 }

e2d-usedFreqThreshold-RSCP-e OBJECT-TYPE
    SYNTAX Signed32 (-115..-25)
    ACCESS read-write
    STATUS optional
    DESCRIPTION "RSCP used frequency threshold (in dBm)"
    ::= { event-2d-inter 3 }

e2d-timeToTrigger-e OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-2d-inter 4 }

e2f-Hysteresis-e OBJECT-TYPE
    SYNTAX Unsigned32 (0..145)
    ACCESS read-write
    STATUS optional
    DESCRIPTION "Actual value Hysteresis = IE value / 10"
    ::= { event-2f-inter 1 }

e2f-usedFreqThreshold-ECNO-e OBJECT-TYPE
    SYNTAX Signed32 (-24..0)
    ACCESS read-write
    STATUS optional
    DESCRIPTION "EcNo used frequency threshold (in dBm)"
    ::= { event-2f-inter 2 }

e2f-usedFreqThreshold-RSCP-e OBJECT-TYPE
    SYNTAX Signed32 (-115..-25)
    ACCESS read-write
    STATUS optional
    DESCRIPTION "RSCP used frequency threshold (in dBm)"
    ::= { event-2f-inter 3 }

e2f-timeToTrigger-e OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-2f-inter 4 }

e2-measurementQuantity OBJECT-TYPE
    SYNTAX Unsigned32 (0..1)
    ACCESS read-write
    STATUS optional
    DESCRIPTION "Measurement Quantity (trigger events on) : 0 = EcNo; 1 = RSCP"
    ::= { interFrequencyHandoverControl 8 }

e2-WfactUsedFreq OBJECT-TYPE
    SYNTAX Unsigned32 (0..20)
    ACCESS read-write
    STATUS optional
    DESCRIPTION "Weighting factor used frequency for events 2A/2B/2C/2D/2F. Actual value W = IE value * 0.1"
    ::= { interFrequencyHandoverControl 9 }

-- Please do not re-use the following (param is obsolete).
--inter-triggerOnEvent OBJECT-TYPE
--    SYNTAX Unsigned32 (0..4)
--    ACCESS read-write
--    STATUS optional
--    DESCRIPTION "Trigger relocation on : 0=event2a, 1=event2b, 2=<default 2a>, 3=<default 2a>, 4=event2c"
--    ::= { interFrequencyHandoverControl 10 }

e2-FilterCoefficient OBJECT-TYPE
    SYNTAX Unsigned32 (0..14)
    ACCESS read-write
    STATUS optional
    DESCRIPTION "Filter Coefficient for Inter Frequency (fc0-fc9, 10=fc11, 11=fc13, 12=fc15, 13=fc17, 14=fc19)"
    ::= { interFrequencyHandoverControl 11}

e2-WfactNonUsedFreq OBJECT-TYPE
    SYNTAX Unsigned32 (0..20)
    ACCESS read-write
    STATUS optional
    DESCRIPTION "Weighting factor non used frequency for events 2A/2B/2C/2D/2F. Actual value W = IE value * 0.1"
    ::= { interFrequencyHandoverControl 12 }
    
e3a-Hysteresis OBJECT-TYPE
    SYNTAX Unsigned32 (0..145)
    ACCESS read-write
    STATUS optional
    DESCRIPTION "Actual value Hysteresis = IE value / 10"
    ::= { event-3a 1 }

e3a-thresholdOtherSystem-RSSI OBJECT-TYPE
    SYNTAX Signed32 (-110..-48)
    ACCESS read-write
    STATUS optional
    DESCRIPTION "RSSI threshold other system (GSM) (in dBm)"
    ::= { event-3a 2 }
    
e3a-thresholdOwnSystem-ECNO OBJECT-TYPE
    SYNTAX Signed32 (-24..0)
    ACCESS read-write
    STATUS optional
    DESCRIPTION "EcNo threshold own system (in dBm)"
    ::= { event-3a 3 }

e3a-thresholdOwnSystem-RSCP OBJECT-TYPE
    SYNTAX Signed32 (-115..-25)
    ACCESS read-write
    STATUS optional
    DESCRIPTION "RSCP threshold own system (in dBm)"
    ::= { event-3a 4 }

e3a-GsmFilterCoefficient OBJECT-TYPE
    SYNTAX Unsigned32 (0..19)
    ACCESS read-write
    STATUS optional
    DESCRIPTION "Filter Coefficient for GSM (fc0-fc9, 10=fc11, 11=fc13, 12=fc15, 13=fc17, 14=fc19)"
    ::= { event-3a 5}

e3a-timeToTrigger OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-3a 6 }
    
e2d-Hysteresis-r OBJECT-TYPE
    SYNTAX Unsigned32 (0..145)
    ACCESS read-write
    STATUS optional
    DESCRIPTION "Actual value Hysteresis = IE value / 10"
    ::= { event-2d-rat 1 }

e2d-usedFreqThreshold-ECNO-r OBJECT-TYPE
    SYNTAX Signed32 (-24..0)
    ACCESS read-write
    STATUS optional
    DESCRIPTION "EcNo used frequency threshold (in dBm)"
    ::= { event-2d-rat 2 }

e2d-usedFreqThreshold-RSCP-r OBJECT-TYPE
    SYNTAX Signed32 (-115..-25)
    ACCESS read-write
    STATUS optional
    DESCRIPTION "RSCP used frequency threshold (in dBm)"
    ::= { event-2d-rat 3 }

e2d-timeToTrigger-r OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-2d-rat 4 }

e2f-Hysteresis-r OBJECT-TYPE
    SYNTAX Unsigned32 (0..145)
    ACCESS read-write
    STATUS optional
    DESCRIPTION "Actual value Hysteresis = IE value / 10"
    ::= { event-2f-rat 1 }

e2f-usedFreqThreshold-ECNO-r OBJECT-TYPE
    SYNTAX Signed32 (-24..0)
    ACCESS read-write
    STATUS optional
    DESCRIPTION "EcNo used frequency threshold (in dBm)"
    ::= { event-2f-rat 2 }

e2f-usedFreqThreshold-RSCP-r OBJECT-TYPE
    SYNTAX Signed32 (-115..-25)
    ACCESS read-write
    STATUS optional
    DESCRIPTION "RSCP used frequency threshold (in dBm)"
    ::= { event-2f-rat 3 }

e2f-timeToTrigger-r OBJECT-TYPE
    SYNTAX Unsigned32 (0..15)
    ACCESS read-write
    STATUS optional
    DESCRIPTION "Time to Trigger (ms) : 0=0;1=10;2=20;3=40;4=60;5=80;6=100;7=120;8=160;9=200;10=240;11=320;12=640;13=1280;14=2560;15=5000"
    ::= { event-2f-rat 4 }
    
e3-measurementQuantity OBJECT-TYPE
    SYNTAX Unsigned32 (0..1)
    ACCESS read-write
    STATUS optional
    DESCRIPTION "Measurement Quantity (trigger events on) : 0 = EcNo; 1 = RSCP"
    ::= { interSystemHandoverControl 8 }
    
e3-Wfact OBJECT-TYPE
    SYNTAX Unsigned32 (0..20)
    ACCESS read-write
    STATUS optional
    DESCRIPTION "Weighting factor used frequency for events 2A/2B/2C/2D/2F. Actual value W = IE value * 0.1"
    ::= { interSystemHandoverControl 9 }
    
e3-UtranFilterCoefficient OBJECT-TYPE
    SYNTAX Unsigned32 (0..19)
    ACCESS read-write
    STATUS optional
    DESCRIPTION "Filter Coefficient for UTRAN (fc0-fc9, 10=fc11, 11=fc13, 12=fc15, 13=fc17, 14=fc19)"
    ::= { interSystemHandoverControl 10 }
    
freqSyncAdminState OBJECT-TYPE
    SYNTAX Unsigned32 (0..1)
    ACCESS read-write
    STATUS optional
    DESCRIPTION "0 = Locked, 1 = Unlocked."
    ::= { freqSync 1 }

freqSyncNtpServer1 OBJECT-TYPE
    SYNTAX IpAddress
    ACCESS read-write
    STATUS optional
    DESCRIPTION "1st NTP server. 0.0.0.0 to disable."
    ::= { freqSync 2 }

freqSyncNtpServer2 OBJECT-TYPE
    SYNTAX IpAddress
    ACCESS read-write
    STATUS optional
    DESCRIPTION "2nd NTP server. 0.0.0.0 to disable."
    ::= { freqSync 3 }

freqSyncNtpServer3 OBJECT-TYPE
    SYNTAX IpAddress
    ACCESS read-write
    STATUS optional
    DESCRIPTION "3rd NTP server. 0.0.0.0 to disable."
    ::= { freqSync 4 }

freqSyncNtpServer4 OBJECT-TYPE
    SYNTAX IpAddress
    ACCESS read-write
    STATUS optional
    DESCRIPTION "4th NTP server. 0.0.0.0 to disable."
    ::= { freqSync 5 }

provisioningParamsSc0 OBJECT-TYPE
    SYNTAX Unsigned32
    ACCESS read-write
    STATUS optional
    DESCRIPTION "Scrambling Code 0, provisioning parameters"
    ::= { provisioningParams 1 }

provisioningParamsSc1 OBJECT-TYPE
    SYNTAX Unsigned32
    ACCESS read-write
    STATUS optional
    DESCRIPTION "Scrambling Code 1, provisioning parameters"
    ::= { provisioningParams 2 }

provisioningParamsSc2 OBJECT-TYPE
    SYNTAX Unsigned32
    ACCESS read-write
    STATUS optional
    DESCRIPTION "Scrambling Code 2, provisioning parameters"
    ::= { provisioningParams 3 }

provisioningParamsSc3 OBJECT-TYPE
    SYNTAX Unsigned32
    ACCESS read-write
    STATUS optional
    DESCRIPTION "Scrambling Code 3, provisioning parameters"
    ::= { provisioningParams 4 }

provisioningParamsSc4 OBJECT-TYPE
    SYNTAX Unsigned32
    ACCESS read-write
    STATUS optional
    DESCRIPTION "Scrambling Code 4, provisioning parameters"
    ::= { provisioningParams 5 }

provisioningParamsSc5 OBJECT-TYPE
    SYNTAX Unsigned32
    ACCESS read-write
    STATUS optional
    DESCRIPTION "Scrambling Code 5, provisioning parameters"
    ::= { provisioningParams 6 }

provisioningParamsSc6 OBJECT-TYPE
    SYNTAX Unsigned32
    ACCESS read-write
    STATUS optional
    DESCRIPTION "Scrambling Code 6, provisioning parameters"
    ::= { provisioningParams 7 }

provisioningParamsSc7 OBJECT-TYPE
    SYNTAX Unsigned32
    ACCESS read-write
    STATUS optional
    DESCRIPTION "Scrambling Code 7, provisioning parameters"
    ::= { provisioningParams 8 }

provisioningParamsSc8 OBJECT-TYPE
    SYNTAX Unsigned32
    ACCESS read-write
    STATUS optional
    DESCRIPTION "Scrambling Code 8, provisioning parameters"
    ::= { provisioningParams 9 }

provisioningParamsSc9 OBJECT-TYPE
    SYNTAX Unsigned32
    ACCESS read-write
    STATUS optional
    DESCRIPTION "Scrambling Code 9, provisioning parameters"
    ::= { provisioningParams 10 }

provisioningParamsNumScs OBJECT-TYPE
    SYNTAX Unsigned32
    ACCESS read-write
    STATUS optional
    DESCRIPTION "Number of Scrambling Codes, provisioning parameters"
    ::= { provisioningParams 11 }


cpichPowerDbm OBJECT-TYPE
    SYNTAX INTEGER (-10..10)
    ACCESS read-write
    STATUS optional
    DESCRIPTION "CPICH power (dBm)
                 May be increased according to results of REM scan (in applicable builds).
                 Cannot be less than 20dBm below totalTxPower."
    ::= { powerControlParams 1 }

initialDpchPowerOffsetDb OBJECT-TYPE
    SYNTAX INTEGER (-28..-3)
    ACCESS read-write
    STATUS optional
    DESCRIPTION "Initial DPCH Power Offset relative to max transmit power (dB)"
    ::= { powerControlParams 2 }

--maxDpchPowerOffsetDb OBJECT-TYPE
--    SYNTAX INTEGER (-10..10)
--    ACCESS read-write
--    STATUS optional
--    DESCRIPTION "Maximum DPCH Power Offset relative to CPICH (dB)"
--    ::= { powerControlParams 3 }

pccpchPowerOffsetDb OBJECT-TYPE
    SYNTAX INTEGER (-10..0)
    ACCESS read-write
    STATUS optional
    DESCRIPTION "PCCPCH Power Offset relative to CPICH (dB)"
    ::= { powerControlParams 4 }

schPowerOffsetDb OBJECT-TYPE
    SYNTAX INTEGER (-10..0)
    ACCESS read-write
    STATUS optional
    DESCRIPTION "SCH Power Offset relative to CPICH (dB)"
    ::= { powerControlParams 5 }

sccpchPowerOffsetDb OBJECT-TYPE
    SYNTAX INTEGER (-10..0)
    ACCESS read-write
    STATUS optional
    DESCRIPTION "SCCPCH Power Offset relative to CPICH (dB)"
    ::= { powerControlParams 6 }

pichPowerOffsetDb OBJECT-TYPE
    SYNTAX INTEGER (-10..0)
    ACCESS read-write
    STATUS optional
    DESCRIPTION "PICH Power Offset relative to CPICH (dB)"
    ::= { powerControlParams 7 }

aichPowerOffsetDb OBJECT-TYPE
    SYNTAX INTEGER (-10..0)
    ACCESS read-write
    STATUS optional
    DESCRIPTION "AICH Power Offset relative to CPICH (dB)"
    ::= { powerControlParams 8 }

hsscchPowerOffsetDb OBJECT-TYPE
    SYNTAX INTEGER (-10..10)
    ACCESS read-write
    STATUS optional
    DESCRIPTION "HSSCCH Power Offset relative to DPCCH pilot bits (dB)"
    ::= { powerControlParams 9 }

maxHspdschPowerOffsetDbTenths OBJECT-TYPE
    SYNTAX INTEGER (-60..130)
    ACCESS read-write
    STATUS optional
    DESCRIPTION "Max HS-PDSCH Power Offset relative to CPICH (x0.1 dB)"
    ::= { powerControlParams 10 }

totalTxPowerDbm OBJECT-TYPE
    SYNTAX INTEGER (-40..30)
    ACCESS read-write
    STATUS optional
    DESCRIPTION "Total TX Power (dBm).
                 Max may be limited by software/hardware build to +15dBm or +20dBm.
                 Auto Config may adjust the actual total transmit power according
                 to the RF environment.  Cannot be more than 20dBm above cpichPowerDbm.
                 See also cpichPowerDbm parameter."
    ::= { powerControlParams 11 }

paGainDb OBJECT-TYPE
    SYNTAX INTEGER (0..30)
    ACCESS read-write
    STATUS optional
    DESCRIPTION "External PA Gain (dB).
                 If an external PA is attached to the HBS2 then this must be
                 set to the actual gain of the PA in order that SIB5 declared
                 CPICH transmit power is set correctly.  This parameter ONLY
                 affects SIB5.  The total TX power and CPICH power parameters
                 must be set for the power required at the *output of the HBS2*
                 i.e. prior to the PA.  Only writeable in products that are
                 expected to support an external PA."
    ::= { powerControlParams 12 }

highRateBearer OBJECT-TYPE
    SYNTAX OCTET STRING (SIZE(0..8))
    ACCESS read-write
    STATUS optional
    DESCRIPTION "Which 384k Bearers are available:
               none, dch384k, hsdpa384k, all"
    ::= { rrmParams 1 }

forcePsBearer OBJECT-TYPE
    SYNTAX OCTET STRING (SIZE(0..8))
    ACCESS read-write
    STATUS optional
    DESCRIPTION "Force the Ps bearer used by every Ue to be either:
               off (normal algorithm used), ps64, ps384, hsdpa64, hsdpa384"
    ::= { rrmParams 2 }

serialNumber OBJECT-TYPE
    SYNTAX OCTET STRING (SIZE(10))
    ACCESS read-write
    STATUS optional
    DESCRIPTION "Unit Serial Number."
    ::= { factory 1 }

oscDac OBJECT-TYPE
    SYNTAX Unsigned32 (0..4095)
    ACCESS read-write
    STATUS optional
    DESCRIPTION "Calibration: Oscillator DAC Value"
    ::= { factory 2 }

rssi OBJECT-TYPE
    SYNTAX Unsigned32 (0..255)
    ACCESS read-only
    STATUS optional
    DESCRIPTION "Current RSSI value (read only)."
    ::= { factory 35 }

rxAttenuator1 OBJECT-TYPE
    SYNTAX Unsigned32 (0..1)
    ACCESS read-write
    STATUS optional
    DESCRIPTION "Enable/Disable RX attenuator 1.
                 Unused on >= 3.1 hardware."
    ::= { factory 37 }

rxAttenuator2 OBJECT-TYPE
    SYNTAX Unsigned32 (0..1)
    ACCESS read-write
    STATUS optional
    DESCRIPTION "Enable/Disable RX attenuator 2.
                 Unused on >= 3.1 hardware."
    ::= { factory 38 }

getFrameAndFrameErrorCount OBJECT-TYPE
    SYNTAX OCTET STRING (SIZE(256))
    ACCESS read-only
    STATUS optional
    DESCRIPTION "Get the Frame Count, Bit Errors, DCH Blocks and DCH Block Errors."
    ::= { factory 46 }

startFrameAndFrameErrorCount OBJECT-TYPE
    SYNTAX Unsigned32 (1..1)
    ACCESS read-write
    STATUS optional
    DESCRIPTION "Reset frame and error counts to zero and start counting."
    ::= { factory 47 }

stopFrameAndFrameErrorCount OBJECT-TYPE
    SYNTAX Unsigned32 (1..1)
    ACCESS read-write
    STATUS optional
    DESCRIPTION "Stop counting frame and error counts."
    ::= { factory 48 }

setRegisterLocation OBJECT-TYPE
    SYNTAX Unsigned32 (0..1023)
    ACCESS read-write
    STATUS optional
    DESCRIPTION "Location of register to read/write."
    ::= { factory 49 }

readMsdRegister OBJECT-TYPE
    SYNTAX Unsigned32 (0..255)
    ACCESS read-only
    STATUS optional
    DESCRIPTION "Read from the MSD register set by setRegisterLocation."
    ::= { factory 50 }

writeMsdRegister OBJECT-TYPE
    SYNTAX Unsigned32 (0..255)
    ACCESS read-write
    STATUS optional
    DESCRIPTION "Write to the MSD register set by setRegisterLocation."
    ::= { factory 51 }

readFpgaRegister OBJECT-TYPE
    SYNTAX Unsigned32 (0..255)
    ACCESS read-only
    STATUS optional
    DESCRIPTION "Read from the FPGA register set by setRegisterLocation."
    ::= { factory 52 }

writeFpgaRegister OBJECT-TYPE
    SYNTAX Unsigned32 (0..255)
    ACCESS read-write
    STATUS optional
    DESCRIPTION "Write to the FPGA register set by setRegisterLocation."
    ::= { factory 53 }

unitMacAddress OBJECT-TYPE
    SYNTAX OCTET STRING (SIZE(17))
    ACCESS read-write
    STATUS optional
    DESCRIPTION "Unit MAC Address.  Will be stored in flash.
                 Requires reboot to take effect.
                 ( e.g. 00:12:34:56:ab:cd )"
    ::= { factory 40 }

buildDesc OBJECT-TYPE
    SYNTAX OCTET STRING (SIZE(1..100))
    ACCESS read-only
    STATUS optional
    DESCRIPTION "Build description."
    ::= { factory 41 }

hardwareType OBJECT-TYPE
    SYNTAX Unsigned32 (0..255)
    ACCESS read-write
    STATUS optional
    DESCRIPTION "Hardware type."
    ::= { factory 42 }

hardwareRevision OBJECT-TYPE
    SYNTAX Unsigned32 (0..255)
    ACCESS read-write
    STATUS optional
    DESCRIPTION "Hardware revision."
    ::= { factory 43 }

hardwareModState OBJECT-TYPE
    SYNTAX Unsigned32 (0..255)
    ACCESS read-write
    STATUS optional
    DESCRIPTION "Hardware modification state."
    ::= { factory 44 }

oscDacSlopePptPerBit OBJECT-TYPE
    SYNTAX INTEGER (-65535..65535)
    ACCESS read-write
    STATUS optional
    DESCRIPTION "Calibration: Oscillator frequency slope (parts per trillion per bit)."
    ::= { factory 45 }

l1l2TraceCriticalityMask OBJECT-TYPE
    SYNTAX Unsigned32 (0..31)
    ACCESS read-write
    STATUS optional
    DESCRIPTION "Logging mask for l1l2 application.  Bit field:
                 fatal(16), critical(8), warning(4), info(2), verbose(1)"
    ::= { trace 1 }

l1l2TraceCategoriesMask OBJECT-TYPE
    SYNTAX Unsigned32 (0..31)
    ACCESS read-write
    STATUS optional
    DESCRIPTION "Logging mask for l1l2 categories.  Bit field:
                 RLC(4), MAC(2), L1(1)"
    ::= { trace 2 }

--
-- TRAPS
--
-- Can add "VARIABLES {someVar }" declaration to these if required.
--

configurationParameterOutOfRangeTrap TRAP-TYPE
    ENTERPRISE traps
    DESCRIPTION "Configuration parameter out-of-range"
    ::= 0

messageChecksumFailureTrap TRAP-TYPE
    ENTERPRISE traps
    DESCRIPTION "Message checksum failure"
    ::= 1

l1HeartbeatFifoCorruptionTrap TRAP-TYPE
    ENTERPRISE traps
    DESCRIPTION "L1 heartbeat FIFO corruption"
    ::= 2

invalidMessageProcedureTrap TRAP-TYPE
    ENTERPRISE traps
    DESCRIPTION "Invalid message procedure"
    ::= 3

invalidMessageTypeTrap TRAP-TYPE
    ENTERPRISE traps
    DESCRIPTION "Invalid message type"
    ::= 4

mncThirdDigitNotCurrentlySupportedTrap TRAP-TYPE
    ENTERPRISE traps
    DESCRIPTION "MNC third digit not currently supported"
    ::= 5

invalid3WayIfMgrIpAddressTrap TRAP-TYPE
    ENTERPRISE traps
    DESCRIPTION "Invalid IP address for 3WayIf manager"
    ::= 6

eepromWriteErrorTrap TRAP-TYPE
    ENTERPRISE traps
    DESCRIPTION "EEPROM write error"
    ::= 7

invalidParameterIdTrap TRAP-TYPE
    ENTERPRISE traps
    DESCRIPTION "Invalid parameter ID"
    ::= 8

testTrap TRAP-TYPE
    ENTERPRISE traps
    DESCRIPTION "Engineering Test Trap - Ignore"
    ::= 9

END
